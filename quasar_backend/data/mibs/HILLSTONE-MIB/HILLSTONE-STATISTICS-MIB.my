-- ******************************************************************************
-- HILLSTONE-STATISTICS-MIB
--
-- Copyright (c) 2009 by Hillstone Networks, Inc.
-- All rights reserved.
--
-- Version:      V3
-- Description:	 Hillstone Networks STATISTICS MIB Object Identifier Assignments
-- ******************************************************************************
--

HILLSTONE-STATISTICS-MIB DEFINITIONS ::= BEGIN

IMPORTS
	hillstoneStatistics		FROM HILLSTONE-SMI
    Counter64, Counter32, Gauge32 FROM SNMPv2-SMI
    Counter, Gauge	FROM RFC1155-SMI
	OBJECT-TYPE		FROM RFC-1212;

          -- textual conventions

          DisplayString ::=
              OCTET STRING
          -- This data type is used to model textual information taken
          -- from the NVT ASCII character set.  By convention, objects
          -- with this syntax are declared as having
          --
          --      SIZE (0..255)

-- System Statistics data

hillstoneSystemStatistics OBJECT IDENTIFIER ::= { hillstoneStatistics 1 }

onlineUserNum OBJECT-TYPE
	SYNTAX INTEGER
	ACCESS read-only
	STATUS mandatory
	::= { hillstoneSystemStatistics 1 }


-- IPSec Statistics data
hillstoneIPSecStatistic OBJECT IDENTIFIER ::= { hillstoneStatistics 2 }

hillstoneIPSecGlobalActiveTunnels OBJECT-TYPE
	SYNTAX Gauge
	MAX-ACCESS read-only
	STATUS current
	DESCRIPTION
		"The total number of currently active  IPSec Phase-2 Tunnels."
	::= { hillstoneIPSecStatistic 1 }

hillstoneIPSecGlobalActiveSas OBJECT-TYPE
	SYNTAX Gauge
	MAX-ACCESS read-only
	STATUS current
	DESCRIPTION
		"The total number of currently active or expiring IPSec Phase-2 SA."
	::= { hillstoneIPSecStatistic 2 }

hillstoneIPSecStatisticTable OBJECT-TYPE
	SYNTAX SEQUENCE OF hillstoneIPSecStatisticEntry
	MAX-ACCESS not-accessible
	STATUS current
	DESCRIPTION
		"The table of the ipsec tunnel flow statistics"
        ::= { hillstoneIPSecStatistic 3 }

hillstoneIPSecStatisticEntry OBJECT-TYPE
	SYNTAX hillstoneIPSecStatisticEntry
	MAX-ACCESS not-accessible
	STATUS current
	DESCRIPTION
		"The entry is used in ip address informatioin of this dns server"
	INDEX { hillstoneIPsecTunnelID }
	::= { hillstoneIPSecStatisticTable 1 }


hillstoneIPSecStatisticEntry ::=
      SEQUENCE{
          hillstoneIPsecTunnelID
	      Counter,
	  hillstoneIPSecInOctets
	      Counter64,
	  hillstoneIPSecInDecompOctets
	      Counter64,
	  hillstoneIPSecInPkts
	      Counter64,
	  hillstoneIPSecInDrops
	      Counter64,
	  hillstoneIPSecInReplayDrops
	      Counter32,
	  hillstoneIPSecInAuthFails
	      Counter32,
	  hillstoneIPSecInDecryptFails
	      Counter32,
	  hillstoneIPSecOutOctets
	      Counter64,
	  hillstoneIPSecOutUncompOctets
	      Counter64,
	  hillstoneIPSecOutPkts
	      Counter64,
	  hillstoneIPSecOutDrops
	      Counter64,
	  hillstoneIPSecOutEncryptFails
	      Counter32,
	  hillstoneIPSecNoMemoryDropPkts
	      Counter32,
	  hillstoneIPSecNoFindSaDropPkts
	      Counter32,
	  hillstoneIPSecQueueFullDropPkts
	      Counter32,
	  hillstoneIPSecInvalidLenDropPkts
	      Counter32,
	  hillstoneIPSecTooLongDropPkts
	      Counter32,
	  hillstoneIPSecInvalidSaDropPkts
	      Counter32
      }

hillstoneIPsecTunnelID OBJECT-TYPE
	SYNTAX Counter
	MAX-ACCESS read-only
	STATUS current
	DESCRIPTION
		"The IPSec tunnel ID"
	::= { hillstoneIPSecStatisticEntry 1 }

hillstoneIPSecInOctets OBJECT-TYPE
	SYNTAX Counter64
	MAX-ACCESS read-only
	STATUS current
	DESCRIPTION
		"The total number of octets received by all current and previous
		 IPSec Phase-2 Tunnels. This value is accumulated BEFORE determining
		 whether or not the packet should be decompressed."
	::= { hillstoneIPSecStatisticEntry 2 }

hillstoneIPSecInDecompOctets OBJECT-TYPE
	SYNTAX Counter64
	MAX-ACCESS read-only
	STATUS current
	DESCRIPTION
		"The total number of decompressed octets received by all current
		 and previous IPSec Phase-2 Tunnels. This value is accumulated
		 AFTER the packet is decompressed."
	::= { hillstoneIPSecStatisticEntry 3 }

hillstoneIPSecInPkts OBJECT-TYPE
	SYNTAX Counter64
	MAX-ACCESS read-only
	STATUS current
	DESCRIPTION
		"The total number of packets received by all current and
		 previous IPSec Phase-2 Tunnels."
	::= { hillstoneIPSecStatisticEntry 4 }

hillstoneIPSecInDrops OBJECT-TYPE
	SYNTAX Counter64
	MAX-ACCESS read-only
	STATUS current
	DESCRIPTION
		"The total number of packets dropped during receiving
		 process by all current and previous IPSec Phase-2
		 Tunnels. "
	::= { hillstoneIPSecStatisticEntry 5 }

hillstoneIPSecInReplayDrops OBJECT-TYPE
	SYNTAX Counter32
	MAX-ACCESS read-only
	STATUS current
	DESCRIPTION
		"The total number of packets dropped during receiving
		 process due to Anti-Replay process by all
		 current and previous IPSec Phase-2 Tunnels."
	::= { hillstoneIPSecStatisticEntry 6 }

hillstoneIPSecInAuthFails OBJECT-TYPE
	SYNTAX Counter32
	MAX-ACCESS read-only
	STATUS current
	DESCRIPTION
		"The total number of inbound authentication's which ended
		 in failure by all current and previous IPSec Phase-2 Tunnels."
	::= { hillstoneIPSecStatisticEntry 7 }

hillstoneIPSecInDecryptFails OBJECT-TYPE
	SYNTAX Counter32
	MAX-ACCESS read-only
	STATUS current
	DESCRIPTION
		"The total number of inbound decryption's which ended in
		 failure by all current and previous IPSec Phase-2 Tunnels."
	::= { hillstoneIPSecStatisticEntry 8 }

hillstoneIPSecOutOctets OBJECT-TYPE
	SYNTAX Counter64
	MAX-ACCESS read-only
	STATUS current
	DESCRIPTION
		"The total number of octets sent by all current and previous
		 IPSec Phase-2 Tunnels. This value is accumulated AFTER
		 determining whether or not the packet should be compressed."
	::= { hillstoneIPSecStatisticEntry 9 }

hillstoneIPSecOutUncompOctets OBJECT-TYPE
	SYNTAX Counter64
	MAX-ACCESS read-only
	STATUS current
	DESCRIPTION
		"The total number of uncompressed octets sent by all current
		 and previous IPSec Phase-2 Tunnels. This value is accumulated
		 BEFORE the packet is compressed."
	::= { hillstoneIPSecStatisticEntry 10 }

hillstoneIPSecOutPkts OBJECT-TYPE
	SYNTAX Counter64
	MAX-ACCESS read-only
	STATUS current
	DESCRIPTION
		"The total number of packets sent by all current and previous
		 IPSec Phase-2 Tunnels."
	::= { hillstoneIPSecStatisticEntry 11 }

hillstoneIPSecOutDrops OBJECT-TYPE
	SYNTAX Counter64
	MAX-ACCESS read-only
	STATUS current
	DESCRIPTION
		"The total number of packets dropped during sending process
		 by all current and previous IPSec Phase-2 Tunnels."
	::= { hillstoneIPSecStatisticEntry 12 }

hillstoneIPSecOutEncryptFails OBJECT-TYPE
	SYNTAX Counter32
	MAX-ACCESS read-only
	STATUS current
	DESCRIPTION
		"The total number of outbound encryption's which ended in failure
		 by all current and previous IPSec Phase-2 Tunnels."
	::= { hillstoneIPSecStatisticEntry 13 }

hillstoneIPSecNoMemoryDropPkts OBJECT-TYPE
	SYNTAX Counter32
	MAX-ACCESS read-only
	STATUS current
	DESCRIPTION
		"The total number of packets dropped due to no enough memory
		 by all current and previous IPSec Phase-2 Tunnels."
	::= { hillstoneIPSecStatisticEntry 14 }

hillstoneIPSecNoFindSaDropPkts OBJECT-TYPE
	SYNTAX Counter32
	MAX-ACCESS read-only
	STATUS current
	DESCRIPTION
		"The total number of packets dropped due to not find SA by
		 all current and previous IPSec Phase-2 Tunnels."
	::= { hillstoneIPSecStatisticEntry 15 }

hillstoneIPSecQueueFullDropPkts OBJECT-TYPE
	SYNTAX Counter32
	MAX-ACCESS read-only
	STATUS current
	DESCRIPTION
		"The total number of packets dropped due to queue full by
		 all current and previous IPSec Phase-2 Tunnels."
	::= { hillstoneIPSecStatisticEntry 16 }

hillstoneIPSecInvalidLenDropPkts OBJECT-TYPE
	SYNTAX Counter32
	MAX-ACCESS read-only
	STATUS current
	DESCRIPTION
		"The total number of packets dropped due to invalid packet
		length by all current and previous IPSec Phase-2 Tunnels."
	::= { hillstoneIPSecStatisticEntry 17 }

hillstoneIPSecTooLongDropPkts OBJECT-TYPE
	SYNTAX Counter32
	MAX-ACCESS read-only
	STATUS current
	DESCRIPTION
		"The total number of packets dropped due to too long packet by
		 all current and previous IPSec Phase-2 Tunnels."
	::= { hillstoneIPSecStatisticEntry 18 }

hillstoneIPSecInvalidSaDropPkts OBJECT-TYPE
	SYNTAX Counter32
	MAX-ACCESS read-only
	STATUS current
	DESCRIPTION
		"The total number of packets dropped due to invalid SA by all
		 current and previous IPSec Phase-2 Tunnels."
	::= { hillstoneIPSecStatisticEntry 19 }



-- IPS Statistics data
hillstoneIpsEventStatistics OBJECT IDENTIFIER ::= { hillstoneStatistics 3 }

hillstoneEventHttpAtk  OBJECT-TYPE
	SYNTAX Counter64
	MAX-ACCESS read-only
	STATUS current
	DESCRIPTION
	"The http attack occurs during the last statistcs period."
	::= { hillstoneIpsEventStatistics 1 }

hillstoneEventFtpAtk  OBJECT-TYPE
	SYNTAX Counter64
	MAX-ACCESS read-only
	STATUS current
	DESCRIPTION
	"The ftp attack occurs during the last statistcs period."
	::= { hillstoneIpsEventStatistics 2 }

hillstoneEventSmtpAtk  OBJECT-TYPE
	SYNTAX Counter64
	MAX-ACCESS read-only
	STATUS current
	DESCRIPTION
	"The Smtp attack occurs during the last statistcs period."
	::= { hillstoneIpsEventStatistics 3 }

hillstoneEventDnsAtk  OBJECT-TYPE
	SYNTAX Counter64
	MAX-ACCESS read-only
	STATUS current
	DESCRIPTION
	"The dns attack occurs during the last statistcs period."
	::= { hillstoneIpsEventStatistics 4 }

hillstoneEventNetbiosAtk  OBJECT-TYPE
	SYNTAX Counter64
	MAX-ACCESS read-only
	STATUS current
	DESCRIPTION
	"The Netbios attack occurs during the last statistcs period."
	::= { hillstoneIpsEventStatistics 5 }

hillstoneEventPop3Atk  OBJECT-TYPE
	SYNTAX Counter64
	MAX-ACCESS read-only
	STATUS current
	DESCRIPTION
	"The pop3 attack occurs during the last statistcs period."
	::= { hillstoneIpsEventStatistics 6 }

hillstoneEventSipAtk  OBJECT-TYPE
	SYNTAX Counter64
	MAX-ACCESS read-only
	STATUS current
	DESCRIPTION
	"The sip attack occurs during the last statistcs period."
	::= { hillstoneIpsEventStatistics 7 }

hillstoneEventH323Atk  OBJECT-TYPE
	SYNTAX Counter64
	MAX-ACCESS read-only
	STATUS current
	DESCRIPTION
	"The h323 attack occurs during the last statistcs period."
	::= { hillstoneIpsEventStatistics 8 }

hillstoneEventImapAtk  OBJECT-TYPE
	SYNTAX Counter64
	MAX-ACCESS read-only
	STATUS current
	DESCRIPTION
	"The imap attack occurs during the last statistcs period."
	::= { hillstoneIpsEventStatistics 9 }

hillstoneEventP2PAtk  OBJECT-TYPE
	SYNTAX Counter64
	MAX-ACCESS read-only
	STATUS current
	DESCRIPTION
	"The P2P attack occurs during the last statistcs period."
	::= { hillstoneIpsEventStatistics 10 }

hillstoneEventImAtk  OBJECT-TYPE
	SYNTAX Counter64
	MAX-ACCESS read-only
	STATUS current
	DESCRIPTION
	"The IM attack occurs during the last statistcs period."
	::= { hillstoneIpsEventStatistics 11 }

hillstoneEventSQLAtk  OBJECT-TYPE
	SYNTAX Counter64
	MAX-ACCESS read-only
	STATUS current
	DESCRIPTION
	"The SQL inspection attack occurs during the last statistcs period."
	::= { hillstoneIpsEventStatistics 12 }

hillstoneEventIPSOthersAtk  OBJECT-TYPE
	SYNTAX Counter64
	MAX-ACCESS read-only
	STATUS current
	DESCRIPTION
	"The others attack occurs during the last statistcs period."
	::= { hillstoneIpsEventStatistics 13 }



hillstoneIpsFlowStatistics OBJECT IDENTIFIER ::= { hillstoneStatistics 4 }

hillstonePktsHttpAtk  OBJECT-TYPE
    SYNTAX Counter64
    MAX-ACCESS read-only
    STATUS current
    DESCRIPTION
    "The http attack packets occurs during the last statistcs period."
    ::= { hillstoneIpsFlowStatistics 1 }

hillstonePktsFtpAtk  OBJECT-TYPE
    SYNTAX Counter64
    MAX-ACCESS read-only
    STATUS current
    DESCRIPTION
    "The ftp attack packets occurs during the last statistcs period."
    ::= { hillstoneIpsFlowStatistics 2 }

hillstonePktsSmtpAtk  OBJECT-TYPE
    SYNTAX Counter64
    MAX-ACCESS read-only
    STATUS current
    DESCRIPTION
    "The Smtp attack packets occurs during the last statistcs period."
    ::= { hillstoneIpsFlowStatistics 3 }

hillstonePktsDnsAtk  OBJECT-TYPE
    SYNTAX Counter64
    MAX-ACCESS read-only
    STATUS current
    DESCRIPTION
    "The dns attack packets occurs during the last statistcs period."
    ::= { hillstoneIpsFlowStatistics 4 }

hillstonePktsNetbiosAtk  OBJECT-TYPE
    SYNTAX Counter64
    MAX-ACCESS read-only
    STATUS current
    DESCRIPTION
    "The Netbios attack packets occurs during the last statistcs period."
    ::= { hillstoneIpsFlowStatistics 5 }

hillstonePktsPop3Atk  OBJECT-TYPE
    SYNTAX Counter64
    MAX-ACCESS read-only
    STATUS current
    DESCRIPTION
    "The pop3 attack packets occurs during the last statistcs period."
    ::= { hillstoneIpsFlowStatistics 6 }

hillstonePktsSipAtk  OBJECT-TYPE
    SYNTAX Counter64
    MAX-ACCESS read-only
    STATUS current
    DESCRIPTION
    "The sip attack packets occurs during the last statistcs period."
    ::= { hillstoneIpsFlowStatistics 7 }

hillstonePktsH323Atk  OBJECT-TYPE
    SYNTAX Counter64
    MAX-ACCESS read-only
    STATUS current
    DESCRIPTION
    "The h323 attack packets occurs during the last statistcs period."
    ::= { hillstoneIpsFlowStatistics 8 }

hillstonePktsImapAtk  OBJECT-TYPE
    SYNTAX Counter64
    MAX-ACCESS read-only
    STATUS current
    DESCRIPTION
    "The imap attack packets occurs during the last statistcs period."
    ::= { hillstoneIpsFlowStatistics 9 }

hillstonePktsP2PAtk  OBJECT-TYPE
    SYNTAX Counter64
    MAX-ACCESS read-only
    STATUS current
    DESCRIPTION
    "The P2P attack packets occurs during the last statistcs period."
    ::= { hillstoneIpsFlowStatistics 10 }

hillstonePktsImAtk  OBJECT-TYPE
    SYNTAX Counter64
    MAX-ACCESS read-only
    STATUS current
    DESCRIPTION
    "The IM attack packets occurs during the last statistcs period."
    ::= { hillstoneIpsFlowStatistics 11 }

hillstonePktsSQLAtk  OBJECT-TYPE
    SYNTAX Counter64
    MAX-ACCESS read-only
    STATUS current
    DESCRIPTION
    "The SQL inspection attack packets occurs during the last statistcs period."
    ::= { hillstoneIpsFlowStatistics 12 }

hillstonePktsIPSOthersAtk  OBJECT-TYPE
    SYNTAX Counter64
    MAX-ACCESS read-only
    STATUS current
    DESCRIPTION
    "The Others attack packets occurs during the last statistcs period."
    ::= { hillstoneIpsFlowStatistics 13 }

hillstoneAVEventStatistics OBJECT IDENTIFIER ::= { hillstoneStatistics 7  }

hillstoneEventAVHttpClear  OBJECT-TYPE
    SYNTAX Counter64
    MAX-ACCESS read-only
    STATUS current
    DESCRIPTION
    "The http protcol's virus which cleared by AV module during the last statistcs period."
    ::= { hillstoneAVEventStatistics 1 }

hillstoneEventAVFtpClear  OBJECT-TYPE
    SYNTAX Counter64
    MAX-ACCESS read-only
    STATUS current
    DESCRIPTION
    "The ftp protcol's virus which cleared by AV module during the last statistcs period."
    ::= { hillstoneAVEventStatistics 2 }

hillstoneEventAVSmtpClear  OBJECT-TYPE
    SYNTAX Counter64
    MAX-ACCESS read-only
    STATUS current
    DESCRIPTION
    "The smtp protcol's virus which cleared by AV module during the last statistcs period."
    ::= { hillstoneAVEventStatistics 3 }

hillstoneEventAVPopClear  OBJECT-TYPE
    SYNTAX Counter64
    MAX-ACCESS read-only
    STATUS current
    DESCRIPTION
    "The pop3 protcol's virus which cleared by AV module during the last statistcs period."
    ::= { hillstoneAVEventStatistics 4 }

hillstoneEventAVImapClear  OBJECT-TYPE
    SYNTAX Counter64
    MAX-ACCESS read-only
    STATUS current
    DESCRIPTION
    "The IMAP which cleared by AV module during the last statistcs period."
    ::= { hillstoneAVEventStatistics 5 }

hillstoneALGStatistic OBJECT IDENTIFIER ::= { hillstoneStatistics 8 }

hillstoneALGSipDialog OBJECT-TYPE
    SYNTAX Counter32
    MAX-ACCESS read-only
    STATUS current
    DESCRIPTION
        "The size of sip dialog currently."
        ::= { hillstoneALGStatistic 1 }

hillstoneALGSipRegister OBJECT-TYPE
    SYNTAX Counter32
    MAX-ACCESS read-only
    STATUS current
    DESCRIPTION
        "The size of sip register currently."
        ::= { hillstoneALGStatistic 2 }

hillstoneALGSipDialogMax OBJECT-TYPE
    SYNTAX Counter32
    MAX-ACCESS read-only
    STATUS current
    DESCRIPTION
        "The size of sip dialog max."
        ::= { hillstoneALGStatistic 3 }

hillstoneALGSipRegisterMax OBJECT-TYPE
    SYNTAX Counter32
    MAX-ACCESS read-only
    STATUS current
    DESCRIPTION
        "The size of sip register max."
        ::= { hillstoneALGStatistic 4 }

hillstoneAtkEventStatisticsTable OBJECT-TYPE
	SYNTAX SEQUENCE OF hillstoneAtkEventStatisticsEntry
	MAX-ACCESS not-accessible
	STATUS current
	DESCRIPTION
		"The table of the ad statistics"
        ::= { hillstoneStatistics 10 }

hillstoneAtkEventStatisticsEntry OBJECT-TYPE
	SYNTAX hillstoneAtkEventStatisticsEntry
	MAX-ACCESS not-accessible
	STATUS current
	DESCRIPTION
		"The entry is used in ad event"
	INDEX { hillstoneAtkEventZoneIdx }
	::= { hillstoneAtkEventStatisticsTable 1 }

hillstoneAtkEventStatisticsEntry ::=
      SEQUENCE{
	  hillstoneAtkEventZoneIdx
		Counter,
	  hillstoneAtkEventZoneName
		OCTET STRING,
      hillstoneAtkEventIpSpoof
		Counter64,
	  hillstoneAtkEventLandAtk
		Counter64,
	  hillstoneAtkEventSmurfAtk
		Counter64,
	  hillstoneAtkEventFraggleAtk
		Counter64,
      hillstoneAtkEventWinnuke
		Counter64,
	  hillstoneAtkEventDnsFlood
		Counter64,
	  hillstoneAtkEventTcpFlood
		Counter64,
	  hillstoneAtkEventSynSourceFlood
		Counter64,
	  hillstoneAtkEventSynDestFlood
		Counter64,
	  hillstoneAtkEventUdpFlood
		Counter64,
	  hillstoneAtkEventIcmpFlood
		Counter64,
      hillstoneAtkEventRedirect
		Counter64,
	  hillstoneAtkEventUnreacheableAtk
		Counter64,
	  hillstoneAtkEventIpSweep
		Counter64,
	  hillstoneAtkEventPortScan
		Counter64,
	  hillstoneAtkEventIpOptAtk
		Counter64,
      hillstoneAtkEventIpOptSrcRoutAtk
		Counter64,
      hillstoneAtkEventIpOptRoutRecord
		Counter64,
      hillstoneAtkEventTraceRoutAtk
		Counter64,
      hillstoneAtkEventTimeStampAtk
		Counter64,
      hillstoneAtkEventPingOfDeathAtk
		Counter64,
      hillstoneAtkEventTearDropAtk
		Counter64,
      hillstoneAtkEventTcpFlagAtk
        Counter64,
      hillstoneAtkEventIpFragAtk
		Counter64,
      hillstoneAtkEventLargeIcmpAtk
		Counter64,
	  hillstoneAtkEventSweepAndScanAtk
		Counter64,
      hillstoneAtkEventHalfConnAtk
		Counter64,
      hillstoneAtkEventFtpBounceAtk
		Counter64,
      hillstoneAtkEventSynProxyAtk
		Counter64,
	  hillstoneAtkEventSynCookieAtk
		Counter64,
	  hillstoneAtkEventTCPAnomalyAtk
		Counter64,
	  hillstoneAtkEventIPDirectedAtk
		Counter64,
	  hillstoneAtkEventAtkOthersAtk
		Counter64
      }

hillstoneAtkEventZoneIdx OBJECT-TYPE
	SYNTAX Counter
	MAX-ACCESS read-only
	STATUS current
	DESCRIPTION
	    "
	    An internal number to distinguish security zone.
	    Different zone has different number.
	    "
::= { hillstoneAtkEventStatisticsEntry 1 }

hillstoneAtkEventZoneName OBJECT-TYPE
	SYNTAX OCTET STRING (SIZE (1..255))
	MAX-ACCESS read-only
	STATUS current
	DESCRIPTION
	    "
	    The name of security zone.
	    Different zone has different name."
::= { hillstoneAtkEventStatisticsEntry 2 }

hillstoneAtkEventIpSpoof  OBJECT-TYPE
    SYNTAX Counter64
    MAX-ACCESS read-only
    STATUS current
    DESCRIPTION
	"The total number of ip spoof attack occurs during last statistcs period."
    ::= { hillstoneAtkEventStatisticsEntry 3 }

hillstoneAtkEventLandAtk  OBJECT-TYPE
    SYNTAX Counter64
    MAX-ACCESS read-only
    STATUS current
    DESCRIPTION
    "The total number of land attack occurs during last statistcs period."
    ::= { hillstoneAtkEventStatisticsEntry 4 }

hillstoneAtkEventSmurfAtk  OBJECT-TYPE
    SYNTAX Counter64
    MAX-ACCESS read-only
    STATUS current
    DESCRIPTION
    "The total number of smurf attack occurs during last statistcs period."
    ::= { hillstoneAtkEventStatisticsEntry 5 }

hillstoneAtkEventFraggleAtk  OBJECT-TYPE
    SYNTAX Counter64
    MAX-ACCESS read-only
    STATUS current
    DESCRIPTION
    "The total number of fraggle attack occurs during last statistcs period."
    ::= { hillstoneAtkEventStatisticsEntry 6 }

hillstoneAtkEventWinnuke  OBJECT-TYPE
    SYNTAX Counter64
    MAX-ACCESS read-only
    STATUS current
    DESCRIPTION
    "The total number of Winnuke attack occurs during last statistcs period."
    ::= { hillstoneAtkEventStatisticsEntry 7 }

hillstoneAtkEventDnsFlood  OBJECT-TYPE
    SYNTAX Counter64
    MAX-ACCESS read-only
    STATUS current
    DESCRIPTION
    "The total number of DNS flood attack occurs during last statistcs period."
    ::= { hillstoneAtkEventStatisticsEntry 8 }

hillstoneAtkEventTcpFlood  OBJECT-TYPE
    SYNTAX Counter64
    MAX-ACCESS read-only
    STATUS current
    DESCRIPTION
    "The total number of TCP flood attack occurs during last statistcs period."
    ::= { hillstoneAtkEventStatisticsEntry 9 }

hillstoneAtkEventSynSourceFlood  OBJECT-TYPE
    SYNTAX Counter64
    MAX-ACCESS read-only
    STATUS current
    DESCRIPTION
    "The total number of syn flood attack occurs during last statistcs period."
    ::= { hillstoneAtkEventStatisticsEntry 10 }

hillstoneAtkEventSynDestFlood  OBJECT-TYPE
    SYNTAX Counter64
    MAX-ACCESS read-only
    STATUS current
    DESCRIPTION
    "The total number of syn flood attack occurs during last statistcs period."
    ::= { hillstoneAtkEventStatisticsEntry 11 }


hillstoneAtkEventUdpFlood  OBJECT-TYPE
    SYNTAX Counter64
    MAX-ACCESS read-only
    STATUS current
    DESCRIPTION
    "The total number of udp flood attack occurs during last statistcs period."
    ::= { hillstoneAtkEventStatisticsEntry 12 }

hillstoneAtkEventIcmpFlood  OBJECT-TYPE
    SYNTAX Counter64
    MAX-ACCESS read-only
    STATUS current
    DESCRIPTION
    "The total number of icmp flood attack occurs during last statistcs period."
    ::= { hillstoneAtkEventStatisticsEntry 13 }

hillstoneAtkEventRedirect  OBJECT-TYPE
    SYNTAX Counter64
    MAX-ACCESS read-only
    STATUS current
    DESCRIPTION
    "The total number of icmp Redirect attack occurs during last statistcs period."
    ::= { hillstoneAtkEventStatisticsEntry 14 }

hillstoneAtkEventUnreacheableAtk  OBJECT-TYPE
    SYNTAX Counter64
    MAX-ACCESS read-only
    STATUS current
    DESCRIPTION
    "The total number of icmp Unreacheable attack occurs during last statistcs period."
    ::= { hillstoneAtkEventStatisticsEntry 15 }

 hillstoneAtkEventIpSweep  OBJECT-TYPE
    SYNTAX Counter64
    MAX-ACCESS read-only
    STATUS current
    DESCRIPTION
    "The total number of icmp Ip sweep attack occurs during last statistcs period."
    ::= { hillstoneAtkEventStatisticsEntry 16 }

 hillstoneAtkEventPortScan  OBJECT-TYPE
    SYNTAX Counter64
    MAX-ACCESS read-only
    STATUS current
    DESCRIPTION
    "The total number of Port scan attack occurs during last statistcs period."
    ::= { hillstoneAtkEventStatisticsEntry 17 }

 hillstoneAtkEventIpOptAtk  OBJECT-TYPE
    SYNTAX Counter64
    MAX-ACCESS read-only
    STATUS current
    DESCRIPTION
    "The total number of Ip Options attack occurs during last statistcs period."
    ::= { hillstoneAtkEventStatisticsEntry 18 }

 hillstoneAtkEventIpOptSrcRoutAtk  OBJECT-TYPE
    SYNTAX Counter64
    MAX-ACCESS read-only
    STATUS current
    DESCRIPTION
    "The total number of Ip option source route attack occurs during last statistcs period."
    ::= { hillstoneAtkEventStatisticsEntry 19 }

 hillstoneAtkEventIpOptRoutRecord  OBJECT-TYPE
    SYNTAX Counter64
    MAX-ACCESS read-only
    STATUS current
    DESCRIPTION
    "The total number of Ip options route record attack occurs during last statistcs period."
    ::= { hillstoneAtkEventStatisticsEntry 20 }

 hillstoneAtkEventTraceRoutAtk  OBJECT-TYPE
    SYNTAX Counter64
    MAX-ACCESS read-only
    STATUS current
    DESCRIPTION
    "The total number of trace route attack occurs during last statistcs period."
    ::= { hillstoneAtkEventStatisticsEntry 21 }

 hillstoneAtkEventTimeStampAtk  OBJECT-TYPE
    SYNTAX Counter64
    MAX-ACCESS read-only
    STATUS current
    DESCRIPTION
    "The total number of Time stamp attack occurs during last statistcs period."
    ::= { hillstoneAtkEventStatisticsEntry 22 }

 hillstoneAtkEventPingOfDeathAtk  OBJECT-TYPE
    SYNTAX Counter64
    MAX-ACCESS read-only
    STATUS current
    DESCRIPTION
    "The total number of Ping of death attack occurs during last statistcs period."
    ::= { hillstoneAtkEventStatisticsEntry 23 }

  hillstoneAtkEventTearDropAtk  OBJECT-TYPE
    SYNTAX Counter64
    MAX-ACCESS read-only
    STATUS current
    DESCRIPTION
    "The total number of Tear drop attack occurs during last statistcs period."
    ::= { hillstoneAtkEventStatisticsEntry 24 }

  hillstoneAtkEventTcpFlagAtk  OBJECT-TYPE
    SYNTAX Counter64
    MAX-ACCESS read-only
    STATUS current
    DESCRIPTION
    "The total number of Tcp flag attack occurs during last statistcs period."
    ::= { hillstoneAtkEventStatisticsEntry 25 }

  hillstoneAtkEventIpFragAtk  OBJECT-TYPE
    SYNTAX Counter64
    MAX-ACCESS read-only
    STATUS current
    DESCRIPTION
    "The total number of IP Fragment attack occurs during last statistcs period."
    ::= { hillstoneAtkEventStatisticsEntry 26 }

  hillstoneAtkEventLargeIcmpAtk  OBJECT-TYPE
    SYNTAX Counter64
    MAX-ACCESS read-only
    STATUS current
    DESCRIPTION
    "The total number of Large ICMP attack occurs during last statistcs period."
    ::= { hillstoneAtkEventStatisticsEntry 27 }

  hillstoneAtkEventSweepAndScanAtk  OBJECT-TYPE
    SYNTAX Counter64
    MAX-ACCESS read-only
    STATUS current
    DESCRIPTION
    "The total number of Both ip-sweep and port-scan attack occurs during last statistcs period."
    ::= { hillstoneAtkEventStatisticsEntry 28 }

  hillstoneAtkEventHalfConnAtk  OBJECT-TYPE
    SYNTAX Counter64
    MAX-ACCESS read-only
    STATUS current
    DESCRIPTION
    "The total number of Too much Half Con of SYN Flood attack occurs during last statistcs period."
    ::= { hillstoneAtkEventStatisticsEntry 29 }

  hillstoneAtkEventFtpBounceAtk  OBJECT-TYPE
    SYNTAX Counter64
    MAX-ACCESS read-only
    STATUS current
    DESCRIPTION
    "The total number of Ftp Bounce attack occurs during last statistcs period."
    ::= { hillstoneAtkEventStatisticsEntry 30 }

hillstoneAtkEventSynProxyAtk   OBJECT-TYPE
    SYNTAX Counter64
    MAX-ACCESS read-only
    STATUS current
    DESCRIPTION
    "The total number of SynProxy attack occurs during last statistcs period."
    ::= { hillstoneAtkEventStatisticsEntry 31 }

hillstoneAtkEventSynCookieAtk  OBJECT-TYPE
    SYNTAX Counter64
    MAX-ACCESS read-only
    STATUS current
    DESCRIPTION
    "The total number of SynCookie attack occurs during last statistcs period."
    ::= { hillstoneAtkEventStatisticsEntry 32 }

hillstoneAtkEventTCPAnomalyAtk  OBJECT-TYPE
    SYNTAX Counter64
    MAX-ACCESS read-only
    STATUS current
    DESCRIPTION
    "The total number of TCPAnomaly attack occurs during last statistcs period."
    ::= { hillstoneAtkEventStatisticsEntry 33 }

hillstoneAtkEventIPDirectedAtk  OBJECT-TYPE
    SYNTAX Counter64
    MAX-ACCESS read-only
    STATUS current
    DESCRIPTION
    "The total number of IPDirected attack occurs during last statistcs period."
    ::= { hillstoneAtkEventStatisticsEntry 34 }

 hillstoneAtkEventAtkOthersAtk  OBJECT-TYPE
    SYNTAX Counter64
    MAX-ACCESS read-only
    STATUS current
    DESCRIPTION
    "The total number of Others attack occurs during last statistcs period."
    ::= { hillstoneAtkEventStatisticsEntry 35 }

hillstoneAtkFlowStatisticsTable OBJECT-TYPE
	SYNTAX SEQUENCE OF hillstoneAtkFlowStatisticsEntry
	MAX-ACCESS not-accessible
	STATUS current
	DESCRIPTION
		"The table of the ad  flow statistics"
        ::= { hillstoneStatistics 11 }

hillstoneAtkFlowStatisticsEntry OBJECT-TYPE
	SYNTAX hillstoneAtkFlowStatisticsEntry
	MAX-ACCESS not-accessible
	STATUS current
	DESCRIPTION
		"The entry is used in ad flow"
	INDEX { hillstoneFlowPktsZoneIdx }
	::= { hillstoneAtkFlowStatisticsTable 1 }

hillstoneAtkFlowStatisticsEntry ::=
      SEQUENCE{
	  hillstoneFlowPktsZoneIdx
		Counter,
	  hillstoneFlowPktsZoneName
		OCTET STRING,
      hillstoneFlowPktsIpSpoof
		Counter64,
	  hillstoneFlowPktsLandAtk
		Counter64,
	  hillstoneFlowPktsSmurfAtk
		Counter64,
	  hillstoneFlowPktsFraggleAtk
		Counter64,
      hillstoneFlowPktsWinnuke
		Counter64,
	  hillstoneFlowPktsDnsFlood
		Counter64,
	  hillstoneFlowPktsTcpFlood
		Counter64,
	  hillstoneFlowPktsSynSourceFlood
		Counter64,
	  hillstoneFlowPktsSynDestFlood
		Counter64,
	  hillstoneFlowPktsSourceUdpFlood
		Counter64,
	  hillstoneFlowPktsIcmpFlood
		Counter64,
      hillstoneFlowPktsRedirect
		Counter64,
	  hillstoneFlowPktsUnreacheableAtk
		Counter64,
	  hillstoneFlowPktsIpSweep
		Counter64,
	  hillstoneFlowPktsPortScan
		Counter64,
	  hillstoneFlowPktsIpOptAtk
		Counter64, 
      hillstoneFlowPktsIpOptSrcRoutAtk
		Counter64,
      hillstoneFlowPktsIpOptRoutRecord
		Counter64,
      hillstoneFlowPktsTraceRoutAtk
		Counter64,
      hillstoneFlowPktsTimeStampAtk
		Counter64,
      hillstoneFlowPktsPingOfDeathAtk
		Counter64,
      hillstoneFlowPktsTearDropAtk
		Counter64,
      hillstoneFlowPktsTcpFlagAtk
        Counter64,
      hillstoneFlowPktsIpFragAtk
		Counter64,
      hillstoneFlowPktsLargeIcmpAtk
		Counter64,
	  hillstoneFlowPktsSweepAndScanAtk
		Counter64,
      hillstoneFlowPktsHalfConnAtk
		Counter64,
      hillstoneFlowPktsFtpBounceAtk
		Counter64,
      hillstoneFlowPktsSynProxyAtk
		Counter64,
	  hillstoneFlowPktsSynCookieAtk
		Counter64,
	  hillstoneFlowPktsTCPAnomalyAtk
		Counter64,
	  hillstoneFlowPktsIPDirectedAtk
		Counter64,
	  hillstoneFlowPktsAtkOthersAtk
		Counter64,
	  hillstoneFlowPktsDestUdpFlood
		Counter64

 	 }

hillstoneFlowPktsZoneIdx OBJECT-TYPE
	SYNTAX Counter
	MAX-ACCESS read-only
	STATUS current
	DESCRIPTION
	    "
	    An internal number to distinguish security zone.
	    Different zone has different number.
	    "
::= { hillstoneAtkFlowStatisticsEntry 1 }

hillstoneFlowPktsZoneName OBJECT-TYPE
	SYNTAX OCTET STRING (SIZE (1..255))
	MAX-ACCESS read-only
	STATUS current
	DESCRIPTION
	    "
	    The name of security zone.
	    Different zone has different name."
::= { hillstoneAtkFlowStatisticsEntry 2 }


hillstoneFlowPktsIpSpoof  OBJECT-TYPE
    SYNTAX Counter64
    MAX-ACCESS read-only
    STATUS current
    DESCRIPTION
    "The total packets of ip spoof attack occurs during last statistcs period."
    ::= { hillstoneAtkFlowStatisticsEntry 3 }

hillstoneFlowPktsLandAtk  OBJECT-TYPE
    SYNTAX Counter64
    MAX-ACCESS read-only
    STATUS current
    DESCRIPTION
    "The total packets of land attack occurs during last statistcs period."
    ::= { hillstoneAtkFlowStatisticsEntry 4 }

hillstoneFlowPktsSmurfAtk  OBJECT-TYPE
    SYNTAX Counter64
    MAX-ACCESS read-only
    STATUS current
    DESCRIPTION
    "The total packets of smurf attack occurs during last statistcs period."
    ::= { hillstoneAtkFlowStatisticsEntry 5 }

hillstoneFlowPktsFraggleAtk  OBJECT-TYPE
    SYNTAX Counter64
    MAX-ACCESS read-only
    STATUS current
    DESCRIPTION
    "The total packets of fraggle attack occurs during last statistcs period."
    ::= { hillstoneAtkFlowStatisticsEntry 6 }

hillstoneFlowPktsWinnuke  OBJECT-TYPE
    SYNTAX Counter64
    MAX-ACCESS read-only
    STATUS current
    DESCRIPTION
    "The total packets of Winnuke attack occurs during last statistcs period."
    ::= { hillstoneAtkFlowStatisticsEntry 7 }

hillstoneFlowPktsDnsFlood  OBJECT-TYPE
    SYNTAX Counter64
    MAX-ACCESS read-only
    STATUS current
    DESCRIPTION
    "The total packets of DNS flood attack occurs during last statistcs period."
    ::= { hillstoneAtkFlowStatisticsEntry 8 }

hillstoneFlowPktsTcpFlood  OBJECT-TYPE
    SYNTAX Counter64
    MAX-ACCESS read-only
    STATUS current
    DESCRIPTION
    "The total packets of TCP flood attack occurs during last statistcs period."
    ::= { hillstoneAtkFlowStatisticsEntry 9 }

hillstoneFlowPktsSynSourceFlood  OBJECT-TYPE
    SYNTAX Counter64
    MAX-ACCESS read-only
    STATUS current
    DESCRIPTION
    "The total packets of syn flood attack occurs during last statistcs period."
    ::= { hillstoneAtkFlowStatisticsEntry 10 }

hillstoneFlowPktsSynDestFlood  OBJECT-TYPE
    SYNTAX Counter64
    MAX-ACCESS read-only
    STATUS current
    DESCRIPTION
    "The total packets of syn flood attack occurs during last statistcs period."
    ::= { hillstoneAtkFlowStatisticsEntry 11 }


hillstoneFlowPktsSourceUdpFlood  OBJECT-TYPE
    SYNTAX Counter64
    MAX-ACCESS read-only
    STATUS current
    DESCRIPTION
    "The total packets of udp flood attack occurs during last statistcs period."
    ::= { hillstoneAtkFlowStatisticsEntry 12 }


hillstoneFlowPktsIcmpFlood  OBJECT-TYPE
    SYNTAX Counter64
    MAX-ACCESS read-only
    STATUS current
    DESCRIPTION
    "The total packets of icmp flood attack occurs during last statistcs period."
    ::= { hillstoneAtkFlowStatisticsEntry 13 }

hillstoneFlowPktsRedirect  OBJECT-TYPE
    SYNTAX Counter64
    MAX-ACCESS read-only
    STATUS current
    DESCRIPTION
    "The total packets of icmp Redirect attack occurs during last statistcs period."
    ::= { hillstoneAtkFlowStatisticsEntry 14 }

hillstoneFlowPktsUnreacheableAtk  OBJECT-TYPE
    SYNTAX Counter64
    MAX-ACCESS read-only
    STATUS current
    DESCRIPTION
    "The total packets of icmp Unreacheable attack occurs during last statistcs period."
    ::= { hillstoneAtkFlowStatisticsEntry 15 }

 hillstoneFlowPktsIpSweep  OBJECT-TYPE
    SYNTAX Counter64
    MAX-ACCESS read-only
    STATUS current
    DESCRIPTION
    "The total packets of icmp Ip sweep attack occurs during last statistcs period."
    ::= { hillstoneAtkFlowStatisticsEntry 16 }

 hillstoneFlowPktsPortScan  OBJECT-TYPE
    SYNTAX Counter64
    MAX-ACCESS read-only
    STATUS current
    DESCRIPTION
    "The total packets of Port scan attack occurs during last statistcs period."
    ::= { hillstoneAtkFlowStatisticsEntry 17 }

 hillstoneFlowPktsIpOptAtk  OBJECT-TYPE
    SYNTAX Counter64
    MAX-ACCESS read-only
    STATUS current
    DESCRIPTION
    "The total packets of Ip Options attack occurs during last statistcs period."
    ::= { hillstoneAtkFlowStatisticsEntry 18 }

 hillstoneFlowPktsIpOptSrcRoutAtk  OBJECT-TYPE
    SYNTAX Counter64
    MAX-ACCESS read-only
    STATUS current
    DESCRIPTION
    "The total packets of Ip option source route attack occurs during last statistcs period."
    ::= { hillstoneAtkFlowStatisticsEntry 19 }

 hillstoneFlowPktsIpOptRoutRecord  OBJECT-TYPE
    SYNTAX Counter64
    MAX-ACCESS read-only
    STATUS current
    DESCRIPTION
    "The total packets of Ip options route record attack occurs during last statistcs period."
    ::= { hillstoneAtkFlowStatisticsEntry 20 }

 hillstoneFlowPktsTraceRoutAtk  OBJECT-TYPE
    SYNTAX Counter64
    MAX-ACCESS read-only
    STATUS current
    DESCRIPTION
    "The total packets of trace route attack occurs during last statistcs period."
    ::= { hillstoneAtkFlowStatisticsEntry 21 }

 hillstoneFlowPktsTimeStampAtk  OBJECT-TYPE
    SYNTAX Counter64
    MAX-ACCESS read-only
    STATUS current
    DESCRIPTION
    "The total packets of Time stamp attack occurs during last statistcs period."
    ::= { hillstoneAtkFlowStatisticsEntry 22 }

 hillstoneFlowPktsPingOfDeathAtk  OBJECT-TYPE
    SYNTAX Counter64
    MAX-ACCESS read-only
    STATUS current
    DESCRIPTION
    "The total packets of Ping of death attack occurs during last statistcs period."
    ::= { hillstoneAtkFlowStatisticsEntry 23 }

  hillstoneFlowPktsTearDropAtk  OBJECT-TYPE
    SYNTAX Counter64
    MAX-ACCESS read-only
    STATUS current
    DESCRIPTION
    "The total packets of Tear drop attack occurs during last statistcs period."
    ::= { hillstoneAtkFlowStatisticsEntry 24 }

  hillstoneFlowPktsTcpFlagAtk  OBJECT-TYPE
    SYNTAX Counter64
    MAX-ACCESS read-only
    STATUS current
    DESCRIPTION
    "The total packets of Tcp flag attack occurs during last statistcs period."
    ::= { hillstoneAtkFlowStatisticsEntry 25 }

  hillstoneFlowPktsIpFragAtk  OBJECT-TYPE
    SYNTAX Counter64
    MAX-ACCESS read-only
    STATUS current
    DESCRIPTION
    "The total packets of IP Fragment attack occurs during last statistcs period."
    ::= { hillstoneAtkFlowStatisticsEntry 26 }

  hillstoneFlowPktsLargeIcmpAtk  OBJECT-TYPE
    SYNTAX Counter64
    MAX-ACCESS read-only
    STATUS current
    DESCRIPTION
    "The total packets of Large ICMP attack occurs during last statistcs period."
    ::= { hillstoneAtkFlowStatisticsEntry 27 }

  hillstoneFlowPktsSweepAndScanAtk  OBJECT-TYPE
    SYNTAX Counter64
    MAX-ACCESS read-only
    STATUS current
    DESCRIPTION
    "The total packets of Both ip-sweep and port-scan attack occurs during last statistcs period."
    ::= { hillstoneAtkFlowStatisticsEntry 28 }

  hillstoneFlowPktsHalfConnAtk  OBJECT-TYPE
    SYNTAX Counter64
    MAX-ACCESS read-only
    STATUS current
    DESCRIPTION
    "The total packets of Too much Half Con of SYN Flood attack occurs during last statistcs period."
    ::= { hillstoneAtkFlowStatisticsEntry 29 }

  hillstoneFlowPktsFtpBounceAtk  OBJECT-TYPE
    SYNTAX Counter64
    MAX-ACCESS read-only
    STATUS current
    DESCRIPTION
    "The total packets of Ftp Bounce attack occurs during last statistcs period."
    ::= { hillstoneAtkFlowStatisticsEntry 30 }

  hillstoneFlowPktsAtkOthersAtk  OBJECT-TYPE
    SYNTAX Counter64
    MAX-ACCESS read-only
    STATUS current
    DESCRIPTION
    "The total packets of others attack occurs during last statistcs period."
    ::= { hillstoneAtkFlowStatisticsEntry 31 }

hillstoneFlowPktsSynProxyAtk  OBJECT-TYPE
    SYNTAX Counter64
    MAX-ACCESS read-only
    STATUS current
    DESCRIPTION
    "The total number of SynProxy attack occurs during last statistcs period."
    ::= { hillstoneAtkFlowStatisticsEntry 32 }

hillstoneFlowPktsSynCookieAtk   OBJECT-TYPE
    SYNTAX Counter64
    MAX-ACCESS read-only
    STATUS current
    DESCRIPTION
    "The total number of SynCookie attack occurs during last statistcs period."
    ::= { hillstoneAtkFlowStatisticsEntry 33 }

hillstoneFlowPktsTCPAnomalyAtk   OBJECT-TYPE
    SYNTAX Counter64
    MAX-ACCESS read-only
    STATUS current
    DESCRIPTION
    "The total number of TCPAnomaly attack occurs during last statistcs period."
    ::= { hillstoneAtkFlowStatisticsEntry 34 }

hillstoneFlowPktsIPDirectedAtk   OBJECT-TYPE
    SYNTAX Counter64
    MAX-ACCESS read-only
    STATUS current
    DESCRIPTION
    "The total number of IPDirected attack occurs during last statistcs period."
    ::= { hillstoneAtkFlowStatisticsEntry 35 }

hillstoneFlowPktsDestUdpFlood  OBJECT-TYPE
    SYNTAX Counter64
    MAX-ACCESS read-only
    STATUS current
    DESCRIPTION
    "The total packets of udp flood attack occurs during last statistcs period."
    ::= { hillstoneAtkFlowStatisticsEntry 36 }

-- sset address books monitor
hillstoneSSetAddressBooksMonitorTable OBJECT-TYPE
	SYNTAX SEQUENCE OF hillstoneSSetAddressBooksEntry
	MAX-ACCESS not-accessible
	STATUS current
	DESCRIPTION
		"The table of the sset address books traffic statistics"
        ::= { hillstoneStatistics 12 }

hillstoneSSetAddressBooksEntry OBJECT-TYPE
	SYNTAX hillstoneSSetAddressBooksEntry
	MAX-ACCESS not-accessible
	STATUS current
	DESCRIPTION
		"The entry is used in sset address books traffic statistics"
	INDEX { hillstoneSSetAddressBookIdx }
	::= { hillstoneSSetAddressBooksMonitorTable 1 }

hillstoneSSetAddressBooksEntry ::=
    SEQUENCE{
	    hillstoneSSetAddressBookIdx
		    Counter,
	    hillstoneSSetAddressBookName
	        OCTET STRING,
        hillstoneSSetAddressBookCurrentUpstreamTraffic
	        Counter64,
        hillstoneSSetAddressBookCurrentDownstreamTraffic
	        Counter64,
        hillstoneSSetAddressBookCurrentSessionCount
	        Gauge32,

        hillstoneSSetAddressBookLastHourUpstreamTraffic
	        Counter64,
        hillstoneSSetAddressBookLastHourDownstreamTraffic
	        Counter64,

        hillstoneSSetAddressBookLastDayUpstreamTraffic
	        Counter64,
        hillstoneSSetAddressBookLastDayDownstreamTraffic
	        Counter64,

        hillstoneSSetAddressBookLastMonthUpstreamTraffic
	        Counter64,
        hillstoneSSetAddressBookLastMonthDownstreamTraffic
	        Counter64
    }


hillstoneSSetAddressBookIdx OBJECT-TYPE
	SYNTAX Counter
	MAX-ACCESS read-only
	STATUS current
	DESCRIPTION
	    "
	    An number between 1 with 32 to distinguish address books.
	    "
::= { hillstoneSSetAddressBooksEntry 1 }

hillstoneSSetAddressBookName OBJECT-TYPE
	SYNTAX OCTET STRING (SIZE (1..255))
	MAX-ACCESS read-only
	STATUS current
	DESCRIPTION
	    "
	    The name of address books.
	    "
::= { hillstoneSSetAddressBooksEntry 2 }


hillstoneSSetAddressBookCurrentUpstreamTraffic  OBJECT-TYPE
    SYNTAX Counter64
    MAX-ACCESS read-only
    STATUS current
    DESCRIPTION
    "The upstream traffic statistics of address book current."
    ::= { hillstoneSSetAddressBooksEntry 3 }

hillstoneSSetAddressBookCurrentDownstreamTraffic  OBJECT-TYPE
    SYNTAX Counter64
    MAX-ACCESS read-only
    STATUS current
    DESCRIPTION
    "The downstream traffic statistics of address book current."
    ::= { hillstoneSSetAddressBooksEntry 4 }

hillstoneSSetAddressBookCurrentSessionCount  OBJECT-TYPE
    SYNTAX Gauge32
    MAX-ACCESS read-only
    STATUS current
    DESCRIPTION
    "The session count statistics of address book current."
    ::= { hillstoneSSetAddressBooksEntry 5 }


hillstoneSSetAddressBookLastHourUpstreamTraffic  OBJECT-TYPE
    SYNTAX Counter64
    MAX-ACCESS read-only
    STATUS current
    DESCRIPTION
    "The upstream traffic statistics of address book during last hour."
    ::= { hillstoneSSetAddressBooksEntry 6 }

hillstoneSSetAddressBookLastHourDownstreamTraffic  OBJECT-TYPE
    SYNTAX Counter64
    MAX-ACCESS read-only
    STATUS current
    DESCRIPTION
    "The downstream traffic statistics of address book during last hour."
    ::= { hillstoneSSetAddressBooksEntry 7 }


hillstoneSSetAddressBookLastDayUpstreamTraffic  OBJECT-TYPE
    SYNTAX Counter64
    MAX-ACCESS read-only
    STATUS current
    DESCRIPTION
    "The upstream traffic statistics of address book during last day."
    ::= { hillstoneSSetAddressBooksEntry 8 }

hillstoneSSetAddressBookLastDayDownstreamTraffic  OBJECT-TYPE
    SYNTAX Counter64
    MAX-ACCESS read-only
    STATUS current
    DESCRIPTION
    "The downstream traffic statistics of address book during last day."
    ::= { hillstoneSSetAddressBooksEntry 9 }

hillstoneSSetAddressBookLastMonthUpstreamTraffic  OBJECT-TYPE
    SYNTAX Counter64
    MAX-ACCESS read-only
    STATUS current
    DESCRIPTION
    "The upstream traffic statistics of address book during last month."
    ::= { hillstoneSSetAddressBooksEntry 10 }

hillstoneSSetAddressBookLastMonthDownstreamTraffic  OBJECT-TYPE
    SYNTAX Counter64
    MAX-ACCESS read-only
    STATUS current
    DESCRIPTION
    "The downstream traffic statistics of address book during last month."
    ::= { hillstoneSSetAddressBooksEntry 11 }

-- sset user rank monitor
hillstoneUserRealTimeRank OBJECT-TYPE
	SYNTAX SEQUENCE OF hillstoneUserRealTimeRankEntry
	MAX-ACCESS not-accessible
	STATUS current
	DESCRIPTION
		"The rank of Real-time Top 32 user traffic information"
        ::= { hillstoneStatistics 13 }

hillstoneUserRealTimeRankEntry OBJECT-TYPE
	SYNTAX hillstoneUserRealTimeRankEntry
	MAX-ACCESS not-accessible
	STATUS current
	INDEX { hillstoneUserRealTimeRankEntryIdx }
	::= { hillstoneUserRealTimeRank 1 }

hillstoneUserRealTimeRankEntry ::=
    SEQUENCE{
	    hillstoneUserRealTimeRankEntryIdx
		    Counter,
	    hillstoneUserRealTimeRankEntryName
	        OCTET STRING,
        hillstoneUserRealTimeRankEntryUpstreamTraffic
	        Counter64,
        hillstoneUserRealTimeRankEntryDownstreamTraffic
	        Counter64,
        hillstoneUserRealTimeRankEntryAllTraffic
	        Counter64,
        hillstoneUserRealTimeRankEntryRealTimeSessionCount
	        Gauge32,
        hillstoneUserRealTimeRankEntryRealTimeSessionCountPercentage
	        OCTET STRING,
        hillstoneUserRealTimeRankEntryAllTrafficPercentage
	        OCTET STRING,

        hillstoneUserRealTimeRankEntryUpstreamTrafficPercentage
	        OCTET STRING,
        hillstoneUserRealTimeRankEntryDownstreamTrafficPercentage
	        OCTET STRING
 	}


hillstoneUserRealTimeRankEntryIdx OBJECT-TYPE
	SYNTAX Counter
	MAX-ACCESS read-only
	STATUS current
	DESCRIPTION
	    "
	    An number between 1 with 32 to distinguish Entry.
	    "
    ::= { hillstoneUserRealTimeRankEntry 1 }

hillstoneUserRealTimeRankEntryName OBJECT-TYPE
	SYNTAX OCTET STRING (SIZE (1..255))
	MAX-ACCESS read-only
	STATUS current
	DESCRIPTION
	    "
	    The name of user.
	    "
    ::= { hillstoneUserRealTimeRankEntry 2 }


hillstoneUserRealTimeRankEntryUpstreamTraffic  OBJECT-TYPE
    SYNTAX Counter64
    MAX-ACCESS read-only
    STATUS current
    DESCRIPTION
    "The upstream traffic statistics of the user."
    ::= { hillstoneUserRealTimeRankEntry 3 }

hillstoneUserRealTimeRankEntryDownstreamTraffic  OBJECT-TYPE
    SYNTAX Counter64
    MAX-ACCESS read-only
    STATUS current
    DESCRIPTION
    "The downstream traffic statistics of the user."
    ::= { hillstoneUserRealTimeRankEntry 4 }

hillstoneUserRealTimeRankEntryAllTraffic  OBJECT-TYPE
    SYNTAX Counter64
    MAX-ACCESS read-only
    STATUS current
    DESCRIPTION
    "The all traffic of the user."
    ::= { hillstoneUserRealTimeRankEntry 5 }


hillstoneUserRealTimeRankEntryRealTimeSessionCount  OBJECT-TYPE
    SYNTAX Gauge32
    MAX-ACCESS read-only
    STATUS current
    DESCRIPTION
    "The real-time session count of the user."
    ::= { hillstoneUserRealTimeRankEntry 6 }

hillstoneUserRealTimeRankEntryRealTimeSessionCountPercentage  OBJECT-TYPE
    SYNTAX OCTET STRING (SIZE (1..7))
    MAX-ACCESS read-only
    STATUS current
    DESCRIPTION
    "Percentage is the number of sessions that a user belongs to as a proportion of all user, and its precision is two decimal places."
    ::= { hillstoneUserRealTimeRankEntry 7 }

hillstoneUserRealTimeRankEntryAllTrafficPercentage  OBJECT-TYPE
    SYNTAX OCTET STRING (SIZE (1..7))
    MAX-ACCESS read-only
    STATUS current
    DESCRIPTION
    "Percentage is the number of traffic that a user belongs to as a proportion of all user, and its precision is two decimal places."
    ::= { hillstoneUserRealTimeRankEntry 8 }

hillstoneUserRealTimeRankEntryUpstreamTrafficPercentage  OBJECT-TYPE
    SYNTAX OCTET STRING (SIZE (1..7))
    MAX-ACCESS read-only
    STATUS current
    DESCRIPTION
    "Percentage is the number of upstream traffic that a user belongs to as a proportion of all user, and its precision is two decimal places."
    ::= { hillstoneUserRealTimeRankEntry 9 }

hillstoneUserRealTimeRankEntryDownstreamTrafficPercentage  OBJECT-TYPE
    SYNTAX OCTET STRING (SIZE (1..7))
    MAX-ACCESS read-only
    STATUS current
    DESCRIPTION
    "Percentage is the number of downstream traffic that a user belongs to as a proportion of all user, and its precision is two decimal places."
    ::= { hillstoneUserRealTimeRankEntry 10 }

hillstoneUserLastHourRank OBJECT-TYPE
	SYNTAX SEQUENCE OF hillstoneUserLastHourRankEntry
	MAX-ACCESS not-accessible
	STATUS current
	DESCRIPTION
		"The rank of Real-time Top 32 user traffic information"
        ::= { hillstoneStatistics 14 }

hillstoneUserLastHourRankEntry OBJECT-TYPE
	SYNTAX hillstoneUserLastHourRankEntry
	MAX-ACCESS not-accessible
	STATUS current
	INDEX { hillstoneUserLastHourRankEntryIdx }
	::= { hillstoneUserLastHourRank 1 }

hillstoneUserLastHourRankEntry ::=
    SEQUENCE{
	    hillstoneUserLastHourRankEntryIdx
		    Counter,
	    hillstoneUserLastHourRankEntryName
	        OCTET STRING,
        hillstoneUserLastHourRankEntryUpstreamTraffic
	        Counter64,
        hillstoneUserLastHourRankEntryDownstreamTraffic
	        Counter64,
        hillstoneUserLastHourRankEntryAllTraffic
	        Counter64,
        hillstoneUserLastHourRankEntryRealTimeSessionCount
	        Gauge32,
        hillstoneUserLastHourRankEntryRealTimeSessionCountPercentage
	        OCTET STRING,
        hillstoneUserLastHourRankEntryAllTrafficPercentage
	        OCTET STRING,

        hillstoneUserLastHourRankEntryUpstreamTrafficPercentage
	        OCTET STRING,
        hillstoneUserLastHourRankEntryDownstreamTrafficPercentage
	        OCTET STRING
 	}


hillstoneUserLastHourRankEntryIdx OBJECT-TYPE
	SYNTAX Counter
	MAX-ACCESS read-only
	STATUS current
	DESCRIPTION
	    "
	    An number between 1 with 32 to distinguish Entry.
	    "
    ::= { hillstoneUserLastHourRankEntry 1 }

hillstoneUserLastHourRankEntryName OBJECT-TYPE
	SYNTAX OCTET STRING (SIZE (1..255))
	MAX-ACCESS read-only
	STATUS current
	DESCRIPTION
	    "
	    The name of user.
	    "
    ::= { hillstoneUserLastHourRankEntry 2 }


hillstoneUserLastHourRankEntryUpstreamTraffic  OBJECT-TYPE
    SYNTAX Counter64
    MAX-ACCESS read-only
    STATUS current
    DESCRIPTION
    "The upstream traffic statistics of the user."
    ::= { hillstoneUserLastHourRankEntry 3 }

hillstoneUserLastHourRankEntryDownstreamTraffic  OBJECT-TYPE
    SYNTAX Counter64
    MAX-ACCESS read-only
    STATUS current
    DESCRIPTION
    "The downstream traffic statistics of the user."
    ::= { hillstoneUserLastHourRankEntry 4 }

hillstoneUserLastHourRankEntryAllTraffic  OBJECT-TYPE
    SYNTAX Counter64
    MAX-ACCESS read-only
    STATUS current
    DESCRIPTION
    "The all traffic of the user."
    ::= { hillstoneUserLastHourRankEntry 5 }


hillstoneUserLastHourRankEntryRealTimeSessionCount  OBJECT-TYPE
    SYNTAX Gauge32
    MAX-ACCESS read-only
    STATUS current
    DESCRIPTION
    "The real-time session count of the user."
    ::= { hillstoneUserLastHourRankEntry 6 }

hillstoneUserLastHourRankEntryRealTimeSessionCountPercentage  OBJECT-TYPE
    SYNTAX OCTET STRING (SIZE (1..7))
    MAX-ACCESS read-only
    STATUS current
    DESCRIPTION
    "Percentage is the number of sessions that a user belongs to as a proportion of all user, and its precision is two decimal places."
    ::= { hillstoneUserLastHourRankEntry 7 }

hillstoneUserLastHourRankEntryAllTrafficPercentage  OBJECT-TYPE
    SYNTAX OCTET STRING (SIZE (1..7))
    MAX-ACCESS read-only
    STATUS current
    DESCRIPTION
    "Percentage is the number of traffic that a user belongs to as a proportion of all user, and its precision is two decimal places."
    ::= { hillstoneUserLastHourRankEntry 8 }

hillstoneUserLastHourRankEntryUpstreamTrafficPercentage  OBJECT-TYPE
    SYNTAX OCTET STRING (SIZE (1..7))
    MAX-ACCESS read-only
    STATUS current
    DESCRIPTION
    "Percentage is the number of upstream traffic that a user belongs to as a proportion of all user, and its precision is two decimal places."
    ::= { hillstoneUserLastHourRankEntry 9 }

hillstoneUserLastHourRankEntryDownstreamTrafficPercentage  OBJECT-TYPE
    SYNTAX OCTET STRING (SIZE (1..7))
    MAX-ACCESS read-only
    STATUS current
    DESCRIPTION
    "Percentage is the number of downstream traffic that a user belongs to as a proportion of all user, and its precision is two decimal places."
    ::= { hillstoneUserLastHourRankEntry 10 }


hillstoneUserLastDayRank OBJECT-TYPE
	SYNTAX SEQUENCE OF hillstoneUserLastDayRankEntry
	MAX-ACCESS not-accessible
	STATUS current
	DESCRIPTION
		"The rank of Real-time Top 32 user traffic information"
        ::= { hillstoneStatistics 15 }

hillstoneUserLastDayRankEntry OBJECT-TYPE
	SYNTAX hillstoneUserLastDayRankEntry
	MAX-ACCESS not-accessible
	STATUS current
	INDEX { hillstoneUserLastDayRankEntryIdx }
	::= { hillstoneUserLastDayRank 1 }

hillstoneUserLastDayRankEntry ::=
    SEQUENCE{
	    hillstoneUserLastDayRankEntryIdx
		    Counter,
	    hillstoneUserLastDayRankEntryName
	        OCTET STRING,
        hillstoneUserLastDayRankEntryUpstreamTraffic
	        Counter64,
        hillstoneUserLastDayRankEntryDownstreamTraffic
	        Counter64,
        hillstoneUserLastDayRankEntryAllTraffic
	        Counter64,
        hillstoneUserLastDayRankEntryRealTimeSessionCount
	        Gauge32,
        hillstoneUserLastDayRankEntryRealTimeSessionCountPercentage
	        OCTET STRING,
        hillstoneUserLastDayRankEntryAllTrafficPercentage
	        OCTET STRING,

        hillstoneUserLastDayRankEntryUpstreamTrafficPercentage
	        OCTET STRING,
        hillstoneUserLastDayRankEntryDownstreamTrafficPercentage
	        OCTET STRING
 	}


hillstoneUserLastDayRankEntryIdx OBJECT-TYPE
	SYNTAX Counter
	MAX-ACCESS read-only
	STATUS current
	DESCRIPTION
	    "
	    An number between 1 with 32 to distinguish Entry.
	    "
    ::= { hillstoneUserLastDayRankEntry 1 }

hillstoneUserLastDayRankEntryName OBJECT-TYPE
	SYNTAX OCTET STRING (SIZE (1..255))
	MAX-ACCESS read-only
	STATUS current
	DESCRIPTION
	    "
	    The name of user.
	    "
    ::= { hillstoneUserLastDayRankEntry 2 }


hillstoneUserLastDayRankEntryUpstreamTraffic  OBJECT-TYPE
    SYNTAX Counter64
    MAX-ACCESS read-only
    STATUS current
    DESCRIPTION
    "The upstream traffic statistics of the user."
    ::= { hillstoneUserLastDayRankEntry 3 }

hillstoneUserLastDayRankEntryDownstreamTraffic  OBJECT-TYPE
    SYNTAX Counter64
    MAX-ACCESS read-only
    STATUS current
    DESCRIPTION
    "The downstream traffic statistics of the user."
    ::= { hillstoneUserLastDayRankEntry 4 }

hillstoneUserLastDayRankEntryAllTraffic  OBJECT-TYPE
    SYNTAX Counter64
    MAX-ACCESS read-only
    STATUS current
    DESCRIPTION
    "The all traffic of the user."
    ::= { hillstoneUserLastDayRankEntry 5 }


hillstoneUserLastDayRankEntryRealTimeSessionCount  OBJECT-TYPE
    SYNTAX Gauge32
    MAX-ACCESS read-only
    STATUS current
    DESCRIPTION
    "The real-time session count of the user."
    ::= { hillstoneUserLastDayRankEntry 6 }

hillstoneUserLastDayRankEntryRealTimeSessionCountPercentage  OBJECT-TYPE
    SYNTAX OCTET STRING (SIZE (1..7))
    MAX-ACCESS read-only
    STATUS current
    DESCRIPTION
    "Percentage is the number of sessions that a user belongs to as a proportion of all user, and its precision is two decimal places."
    ::= { hillstoneUserLastDayRankEntry 7 }

hillstoneUserLastDayRankEntryAllTrafficPercentage  OBJECT-TYPE
    SYNTAX OCTET STRING (SIZE (1..7))
    MAX-ACCESS read-only
    STATUS current
    DESCRIPTION
    "Percentage is the number of traffic that a user belongs to as a proportion of all user, and its precision is two decimal places."
    ::= { hillstoneUserLastDayRankEntry 8 }

hillstoneUserLastDayRankEntryUpstreamTrafficPercentage  OBJECT-TYPE
    SYNTAX OCTET STRING (SIZE (1..7))
    MAX-ACCESS read-only
    STATUS current
    DESCRIPTION
    "Percentage is the number of upstream traffic that a user belongs to as a proportion of all user, and its precision is two decimal places."
    ::= { hillstoneUserLastDayRankEntry 9 }

hillstoneUserLastDayRankEntryDownstreamTrafficPercentage  OBJECT-TYPE
    SYNTAX OCTET STRING (SIZE (1..7))
    MAX-ACCESS read-only
    STATUS current
    DESCRIPTION
    "Percentage is the number of downstream traffic that a user belongs to as a proportion of all user, and its precision is two decimal places."
    ::= { hillstoneUserLastDayRankEntry 10 }

hillstoneUserLastMonthRank OBJECT-TYPE
	SYNTAX SEQUENCE OF hillstoneUserLastMonthRankEntry
	MAX-ACCESS not-accessible
	STATUS current
	DESCRIPTION
		"The rank of Real-time Top 32 user traffic information"
        ::= { hillstoneStatistics 16 }

hillstoneUserLastMonthRankEntry OBJECT-TYPE
	SYNTAX hillstoneUserLastMonthRankEntry
	MAX-ACCESS not-accessible
	STATUS current
	INDEX { hillstoneUserLastMonthRankEntryIdx }
	::= { hillstoneUserLastMonthRank 1 }

hillstoneUserLastMonthRankEntry ::=
    SEQUENCE{
	    hillstoneUserLastMonthRankEntryIdx
		    Counter,
	    hillstoneUserLastMonthRankEntryName
	        OCTET STRING,
        hillstoneUserLastMonthRankEntryUpstreamTraffic
	        Counter64,
        hillstoneUserLastMonthRankEntryDownstreamTraffic
	        Counter64,
        hillstoneUserLastMonthRankEntryAllTraffic
	        Counter64,
        hillstoneUserLastMonthRankEntryRealTimeSessionCount
	        Gauge32,
        hillstoneUserLastMonthRankEntryRealTimeSessionCountPercentage
	        OCTET STRING,
        hillstoneUserLastMonthRankEntryAllTrafficPercentage
	        OCTET STRING,

        hillstoneUserLastMonthRankEntryUpstreamTrafficPercentage
	        OCTET STRING,
        hillstoneUserLastMonthRankEntryDownstreamTrafficPercentage
	        OCTET STRING
 	}


hillstoneUserLastMonthRankEntryIdx OBJECT-TYPE
	SYNTAX Counter
	MAX-ACCESS read-only
	STATUS current
	DESCRIPTION
	    "
	    An number between 1 with 32 to distinguish Entry.
	    "
    ::= { hillstoneUserLastMonthRankEntry 1 }

hillstoneUserLastMonthRankEntryName OBJECT-TYPE
	SYNTAX OCTET STRING (SIZE (1..255))
	MAX-ACCESS read-only
	STATUS current
	DESCRIPTION
	    "
	    The name of user.
	    "
    ::= { hillstoneUserLastMonthRankEntry 2 }


hillstoneUserLastMonthRankEntryUpstreamTraffic  OBJECT-TYPE
    SYNTAX Counter64
    MAX-ACCESS read-only
    STATUS current
    DESCRIPTION
    "The upstream traffic statistics of the user."
    ::= { hillstoneUserLastMonthRankEntry 3 }

hillstoneUserLastMonthRankEntryDownstreamTraffic  OBJECT-TYPE
    SYNTAX Counter64
    MAX-ACCESS read-only
    STATUS current
    DESCRIPTION
    "The downstream traffic statistics of the user."
    ::= { hillstoneUserLastMonthRankEntry 4 }

hillstoneUserLastMonthRankEntryAllTraffic  OBJECT-TYPE
    SYNTAX Counter64
    MAX-ACCESS read-only
    STATUS current
    DESCRIPTION
    "The all traffic of the user."
    ::= { hillstoneUserLastMonthRankEntry 5 }


hillstoneUserLastMonthRankEntryRealTimeSessionCount  OBJECT-TYPE
    SYNTAX Gauge32
    MAX-ACCESS read-only
    STATUS current
    DESCRIPTION
    "The real-time session count of the user."
    ::= { hillstoneUserLastMonthRankEntry 6 }

hillstoneUserLastMonthRankEntryRealTimeSessionCountPercentage  OBJECT-TYPE
    SYNTAX OCTET STRING (SIZE (1..7))
    MAX-ACCESS read-only
    STATUS current
    DESCRIPTION
    "Percentage is the number of sessions that a user belongs to as a proportion of all user, and its precision is two decimal places."
    ::= { hillstoneUserLastMonthRankEntry 7 }

hillstoneUserLastMonthRankEntryAllTrafficPercentage  OBJECT-TYPE
    SYNTAX OCTET STRING (SIZE (1..7))
    MAX-ACCESS read-only
    STATUS current
    DESCRIPTION
    "Percentage is the number of traffic that a user belongs to as a proportion of all user, and its precision is two decimal places."
    ::= { hillstoneUserLastMonthRankEntry 8 }

hillstoneUserLastMonthRankEntryUpstreamTrafficPercentage  OBJECT-TYPE
    SYNTAX OCTET STRING (SIZE (1..7))
    MAX-ACCESS read-only
    STATUS current
    DESCRIPTION
    "Percentage is the number of upstream traffic that a user belongs to as a proportion of all user, and its precision is two decimal places."
    ::= { hillstoneUserLastMonthRankEntry 9 }

hillstoneUserLastMonthRankEntryDownstreamTrafficPercentage  OBJECT-TYPE
    SYNTAX OCTET STRING (SIZE (1..7))
    MAX-ACCESS read-only
    STATUS current
    DESCRIPTION
    "Percentage is the number of downstream traffic that a user belongs to as a proportion of all user, and its precision is two decimal places."
    ::= { hillstoneUserLastMonthRankEntry 10 }

-- sset App rank monitor
hillstoneAppRealTimeRank OBJECT-TYPE
	SYNTAX SEQUENCE OF hillstoneAppRealTimeRankEntry
	MAX-ACCESS not-accessible
	STATUS current
	DESCRIPTION
		"The rank of Real-time Top 32 App traffic information"
        ::= { hillstoneStatistics 17 }

hillstoneAppRealTimeRankEntry OBJECT-TYPE
	SYNTAX hillstoneAppRealTimeRankEntry
	MAX-ACCESS not-accessible
	STATUS current
	INDEX { hillstoneAppRealTimeRankEntryIdx }
	::= { hillstoneAppRealTimeRank 1 }

hillstoneAppRealTimeRankEntry ::=
    SEQUENCE{
	    hillstoneAppRealTimeRankEntryIdx
		    Counter,
	    hillstoneAppRealTimeRankEntryName
	        OCTET STRING,
        hillstoneAppRealTimeRankEntryAppCategory
	        OCTET STRING,
        hillstoneAppRealTimeRankEntryAppSubCategory
	        OCTET STRING,
        hillstoneAppRealTimeRankEntryTraffic
	        Counter64,
        hillstoneAppRealTimeRankEntryTrafficPercentage
	        OCTET STRING,
        hillstoneAppRealTimeRankEntrySessionCount
	        Gauge32,
        hillstoneAppRealTimeRankEntrySessionCountPercentage
	        OCTET STRING
 	}


hillstoneAppRealTimeRankEntryIdx OBJECT-TYPE
	SYNTAX Counter
	MAX-ACCESS read-only
	STATUS current
	DESCRIPTION
	    "
	    An number between 1 with 32 to distinguish Entry.
	    "
    ::= { hillstoneAppRealTimeRankEntry 1 }

hillstoneAppRealTimeRankEntryName OBJECT-TYPE
	SYNTAX OCTET STRING (SIZE (1..255))
	MAX-ACCESS read-only
	STATUS current
    ::= { hillstoneAppRealTimeRankEntry 2 }

hillstoneAppRealTimeRankEntryAppCategory  OBJECT-TYPE
    SYNTAX OCTET STRING (SIZE (1..96))
    MAX-ACCESS read-only
    STATUS current
    ::= { hillstoneAppRealTimeRankEntry 3 }

hillstoneAppRealTimeRankEntryAppSubCategory  OBJECT-TYPE
    SYNTAX OCTET STRING (SIZE (1..96))
    MAX-ACCESS read-only
    STATUS current
    ::= { hillstoneAppRealTimeRankEntry 4 }

hillstoneAppRealTimeRankEntryTraffic  OBJECT-TYPE
    SYNTAX Counter64
    MAX-ACCESS read-only
    STATUS current
    DESCRIPTION
    "The traffic of the App."
    ::= { hillstoneAppRealTimeRankEntry 5 }


hillstoneAppRealTimeRankEntryTrafficPercentage  OBJECT-TYPE
    SYNTAX OCTET STRING (SIZE (1..7))
    MAX-ACCESS read-only
    STATUS current
    DESCRIPTION
    "Percentage is the number of traffic that a App belongs to as a proportion of all App, and its precision is two decimal places."
    ::= { hillstoneAppRealTimeRankEntry 6 }

hillstoneAppRealTimeRankEntrySessionCount  OBJECT-TYPE
    SYNTAX Gauge32
    MAX-ACCESS read-only
    STATUS current
    DESCRIPTION
    "The real-time session count of the App."
    ::= { hillstoneAppRealTimeRankEntry 7 }

hillstoneAppRealTimeRankEntrySessionCountPercentage  OBJECT-TYPE
    SYNTAX OCTET STRING (SIZE (1..7))
    MAX-ACCESS read-only
    STATUS current
    DESCRIPTION
    "Percentage is the number of sessions that a App belongs to as a proportion of all App, and its precision is two decimal places."
    ::= { hillstoneAppRealTimeRankEntry 8 }

-- sset App rank monitor
hillstoneAppLastHourRank OBJECT-TYPE
	SYNTAX SEQUENCE OF hillstoneAppLastHourRankEntry
	MAX-ACCESS not-accessible
	STATUS current
	DESCRIPTION
		"The rank of Real-time Top 32 App traffic information"
        ::= { hillstoneStatistics 18 }

hillstoneAppLastHourRankEntry OBJECT-TYPE
	SYNTAX hillstoneAppLastHourRankEntry
	MAX-ACCESS not-accessible
	STATUS current
	INDEX { hillstoneAppLastHourRankEntryIdx }
	::= { hillstoneAppLastHourRank 1 }

hillstoneAppLastHourRankEntry ::=
    SEQUENCE{
	    hillstoneAppLastHourRankEntryIdx
		    Counter,
	    hillstoneAppLastHourRankEntryName
	        OCTET STRING,
        hillstoneAppLastHourRankEntryAppCategory
	        OCTET STRING,
        hillstoneAppLastHourRankEntryAppSubCategory
	        OCTET STRING,
        hillstoneAppLastHourRankEntryTraffic
	        Counter64,
        hillstoneAppLastHourRankEntryTrafficPercentage
	        OCTET STRING,
        hillstoneAppLastHourRankEntrySessionCount
	        Gauge32,
        hillstoneAppLastHourRankEntrySessionCountPercentage
	        OCTET STRING
 	}


hillstoneAppLastHourRankEntryIdx OBJECT-TYPE
	SYNTAX Counter
	MAX-ACCESS read-only
	STATUS current
	DESCRIPTION
	    "
	    An number between 1 with 32 to distinguish Entry.
	    "
    ::= { hillstoneAppLastHourRankEntry 1 }

hillstoneAppLastHourRankEntryName OBJECT-TYPE
	SYNTAX OCTET STRING (SIZE (1..255))
	MAX-ACCESS read-only
	STATUS current
    ::= { hillstoneAppLastHourRankEntry 2 }

hillstoneAppLastHourRankEntryAppCategory  OBJECT-TYPE
    SYNTAX OCTET STRING (SIZE (1..96))
    MAX-ACCESS read-only
    STATUS current
    ::= { hillstoneAppLastHourRankEntry 3 }

hillstoneAppLastHourRankEntryAppSubCategory  OBJECT-TYPE
    SYNTAX OCTET STRING (SIZE (1..96))
    MAX-ACCESS read-only
    STATUS current
    ::= { hillstoneAppLastHourRankEntry 4 }

hillstoneAppLastHourRankEntryTraffic  OBJECT-TYPE
    SYNTAX Counter64
    MAX-ACCESS read-only
    STATUS current
    DESCRIPTION
    "The traffic of the App."
    ::= { hillstoneAppLastHourRankEntry 5 }


hillstoneAppLastHourRankEntryTrafficPercentage  OBJECT-TYPE
    SYNTAX OCTET STRING (SIZE (1..7))
    MAX-ACCESS read-only
    STATUS current
    DESCRIPTION
    "Percentage is the number of traffic that a App belongs to as a proportion of all App, and its precision is two decimal places."
    ::= { hillstoneAppLastHourRankEntry 6 }

hillstoneAppLastHourRankEntrySessionCount  OBJECT-TYPE
    SYNTAX Gauge32
    MAX-ACCESS read-only
    STATUS current
    DESCRIPTION
    "The real-time session count of the App."
    ::= { hillstoneAppLastHourRankEntry 7 }

hillstoneAppLastHourRankEntrySessionCountPercentage  OBJECT-TYPE
    SYNTAX OCTET STRING (SIZE (1..7))
    MAX-ACCESS read-only
    STATUS current
    DESCRIPTION
    "Percentage is the number of sessions that a App belongs to as a proportion of all App, and its precision is two decimal places."
    ::= { hillstoneAppLastHourRankEntry 8 }
-- sset App rank monitor
hillstoneAppLastDayRank OBJECT-TYPE
	SYNTAX SEQUENCE OF hillstoneAppLastDayRankEntry
	MAX-ACCESS not-accessible
	STATUS current
	DESCRIPTION
		"The rank of Real-time Top 32 App traffic information"
        ::= { hillstoneStatistics 19 }

hillstoneAppLastDayRankEntry OBJECT-TYPE
	SYNTAX hillstoneAppLastDayRankEntry
	MAX-ACCESS not-accessible
	STATUS current
	INDEX { hillstoneAppLastDayRankEntryIdx }
	::= { hillstoneAppLastDayRank 1 }

hillstoneAppLastDayRankEntry ::=
    SEQUENCE{
	    hillstoneAppLastDayRankEntryIdx
		    Counter,
	    hillstoneAppLastDayRankEntryName
	        OCTET STRING,
        hillstoneAppLastDayRankEntryAppCategory
	        OCTET STRING,
        hillstoneAppLastDayRankEntryAppSubCategory
	        OCTET STRING,
        hillstoneAppLastDayRankEntryTraffic
	        Counter64,
        hillstoneAppLastDayRankEntryTrafficPercentage
	        OCTET STRING,
        hillstoneAppLastDayRankEntrySessionCount
	        Gauge32,
        hillstoneAppLastDayRankEntrySessionCountPercentage
	        OCTET STRING
 	}


hillstoneAppLastDayRankEntryIdx OBJECT-TYPE
	SYNTAX Counter
	MAX-ACCESS read-only
	STATUS current
	DESCRIPTION
	    "
	    An number between 1 with 32 to distinguish Entry.
	    "
    ::= { hillstoneAppLastDayRankEntry 1 }

hillstoneAppLastDayRankEntryName OBJECT-TYPE
	SYNTAX OCTET STRING (SIZE (1..255))
	MAX-ACCESS read-only
	STATUS current
    ::= { hillstoneAppLastDayRankEntry 2 }

hillstoneAppLastDayRankEntryAppCategory  OBJECT-TYPE
    SYNTAX OCTET STRING (SIZE (1..96))
    MAX-ACCESS read-only
    STATUS current
    ::= { hillstoneAppLastDayRankEntry 3 }

hillstoneAppLastDayRankEntryAppSubCategory  OBJECT-TYPE
    SYNTAX OCTET STRING (SIZE (1..96))
    MAX-ACCESS read-only
    STATUS current
    ::= { hillstoneAppLastDayRankEntry 4 }

hillstoneAppLastDayRankEntryTraffic  OBJECT-TYPE
    SYNTAX Counter64
    MAX-ACCESS read-only
    STATUS current
    DESCRIPTION
    "The traffic of the App."
    ::= { hillstoneAppLastDayRankEntry 5 }


hillstoneAppLastDayRankEntryTrafficPercentage  OBJECT-TYPE
    SYNTAX OCTET STRING (SIZE (1..7))
    MAX-ACCESS read-only
    STATUS current
    DESCRIPTION
    "Percentage is the number of traffic that a App belongs to as a proportion of all App, and its precision is two decimal places."
    ::= { hillstoneAppLastDayRankEntry 6 }

hillstoneAppLastDayRankEntrySessionCount  OBJECT-TYPE
    SYNTAX Gauge32
    MAX-ACCESS read-only
    STATUS current
    DESCRIPTION
    "The real-time session count of the App."
    ::= { hillstoneAppLastDayRankEntry 7 }

hillstoneAppLastDayRankEntrySessionCountPercentage  OBJECT-TYPE
    SYNTAX OCTET STRING (SIZE (1..7))
    MAX-ACCESS read-only
    STATUS current
    DESCRIPTION
    "Percentage is the number of sessions that a App belongs to as a proportion of all App, and its precision is two decimal places."
    ::= { hillstoneAppLastDayRankEntry 8 }

-- sset App rank monitor
hillstoneAppLastMonthRank OBJECT-TYPE
	SYNTAX SEQUENCE OF hillstoneAppLastMonthRankEntry
	MAX-ACCESS not-accessible
	STATUS current
	DESCRIPTION
		"The rank of Real-time Top 32 App traffic information"
        ::= { hillstoneStatistics 20 }

hillstoneAppLastMonthRankEntry OBJECT-TYPE
	SYNTAX hillstoneAppLastMonthRankEntry
	MAX-ACCESS not-accessible
	STATUS current
	INDEX { hillstoneAppLastMonthRankEntryIdx }
	::= { hillstoneAppLastMonthRank 1 }

hillstoneAppLastMonthRankEntry ::=
    SEQUENCE{
	    hillstoneAppLastMonthRankEntryIdx
		    Counter,
	    hillstoneAppLastMonthRankEntryName
	        OCTET STRING,
        hillstoneAppLastMonthRankEntryAppCategory
	        OCTET STRING,
        hillstoneAppLastMonthRankEntryAppSubCategory
	        OCTET STRING,
        hillstoneAppLastMonthRankEntryTraffic
	        Counter64,
        hillstoneAppLastMonthRankEntryTrafficPercentage
	        OCTET STRING,
        hillstoneAppLastMonthRankEntrySessionCount
	        Gauge32,
        hillstoneAppLastMonthRankEntrySessionCountPercentage
	        OCTET STRING
 	}


hillstoneAppLastMonthRankEntryIdx OBJECT-TYPE
	SYNTAX Counter
	MAX-ACCESS read-only
	STATUS current
	DESCRIPTION
	    "
	    An number between 1 with 32 to distinguish Entry.
	    "
    ::= { hillstoneAppLastMonthRankEntry 1 }

hillstoneAppLastMonthRankEntryName OBJECT-TYPE
	SYNTAX OCTET STRING (SIZE (1..255))
	MAX-ACCESS read-only
	STATUS current
    ::= { hillstoneAppLastMonthRankEntry 2 }

hillstoneAppLastMonthRankEntryAppCategory  OBJECT-TYPE
    SYNTAX OCTET STRING (SIZE (1..96))
    MAX-ACCESS read-only
    STATUS current
    ::= { hillstoneAppLastMonthRankEntry 3 }

hillstoneAppLastMonthRankEntryAppSubCategory  OBJECT-TYPE
    SYNTAX OCTET STRING (SIZE (1..96))
    MAX-ACCESS read-only
    STATUS current
    ::= { hillstoneAppLastMonthRankEntry 4 }

hillstoneAppLastMonthRankEntryTraffic  OBJECT-TYPE
    SYNTAX Counter64
    MAX-ACCESS read-only
    STATUS current
    DESCRIPTION
    "The traffic of the App."
    ::= { hillstoneAppLastMonthRankEntry 5 }


hillstoneAppLastMonthRankEntryTrafficPercentage  OBJECT-TYPE
    SYNTAX OCTET STRING (SIZE (1..7))
    MAX-ACCESS read-only
    STATUS current
    DESCRIPTION
    "Percentage is the number of traffic that a App belongs to as a proportion of all App, and its precision is two decimal places."
    ::= { hillstoneAppLastMonthRankEntry 6 }

hillstoneAppLastMonthRankEntrySessionCount  OBJECT-TYPE
    SYNTAX Gauge32
    MAX-ACCESS read-only
    STATUS current
    DESCRIPTION
    "The real-time session count of the App."
    ::= { hillstoneAppLastMonthRankEntry 7 }

hillstoneAppLastMonthRankEntrySessionCountPercentage  OBJECT-TYPE
    SYNTAX OCTET STRING (SIZE (1..7))
    MAX-ACCESS read-only
    STATUS current
    DESCRIPTION
    "Percentage is the number of sessions that a App belongs to as a proportion of all App, and its precision is two decimal places."
    ::= { hillstoneAppLastMonthRankEntry 8 }

END
