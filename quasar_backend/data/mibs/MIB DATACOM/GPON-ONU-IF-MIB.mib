-- Generated by
-- confdc ++emit-mib GPON-ONU-IF-MIB.mib ++oid 1.3.6.1.4.1.3709.3.6.2 ++join-names force-capitalize ++top gponOnuIfMIB ++module GPON-ONU-IF-MIB -f /opt/dmos/output_pd2905/host//opt/confd/etc/confd/ietf-inet-types.fxs /opt/dmos/output_pd2905/host//opt/confd/etc/confd/ietf-yang-types.fxs /opt/dmos/output_pd2905/host/powerpc-buildroot-linux-gnu/sysroot/etc/confd/IANAifType-MIB.fxs /opt/dmos/output_pd2905/host/powerpc-buildroot-linux-gnu/sysroot/etc/confd/dmos-base.fxs /opt/dmos/output_pd2905/host/powerpc-buildroot-linux-gnu/sysroot/etc/confd/dmos-interfaces.fxs /opt/dmos/output_pd2905/host/powerpc-buildroot-linux-gnu/sysroot/etc/confd/dmos-types.fxs ++ /opt/dmos/output_pd2905/build/dmos-gpond-2e880448ade83811f992ba60702d484eed04efc4/dmos-gpon-onu-mib.fxs
-- 2024-08-14 17:02:59
-- Namespace: urn:dmos-gpon-onu-mib

GPON-ONU-IF-MIB DEFINITIONS ::= BEGIN
IMPORTS
    MODULE-IDENTITY, OBJECT-TYPE,
    Integer32, Unsigned32, Counter32, Counter64,
    Gauge32, IpAddress, TimeTicks
        FROM SNMPv2-SMI
    TEXTUAL-CONVENTION, RowStatus, DateAndTime,
    TruthValue
        FROM SNMPv2-TC
;

gponOnuIfMIB MODULE-IDENTITY
    LAST-UPDATED "202012200000Z"
    ORGANIZATION "@ORGANIZATION"
    CONTACT-INFO "@CONTACT-INFO"
    DESCRIPTION "This module contains GPON ONU and UNI interfaces operational data for SNMP"
    REVISION "202012200000Z"
    DESCRIPTION "@REVISION-DESCRIPTION"
    ::= { 1 3 6 1 4 1 3709 3 6 2 }

String ::= TEXTUAL-CONVENTION
    DISPLAY-HINT "1t"
    STATUS      current
    DESCRIPTION "xs:string"
    SYNTAX      OCTET STRING

-- tagpath /status/interface/ifTable/ifEntry
onuIfTable OBJECT-TYPE
    SYNTAX      SEQUENCE OF OnuIfEntry
    MAX-ACCESS  not-accessible
    STATUS      current
    DESCRIPTION "This table represents ONU associated entities (e.g. ONU, Ethernet UNI)"
    ::= { gponOnuIfMIB 1 }

-- tagpath /status/interface/ifTable/ifEntry
onuIfEntry OBJECT-TYPE
    SYNTAX      OnuIfEntry
    MAX-ACCESS  not-accessible
    STATUS      current
    DESCRIPTION ""
    INDEX { onuifIndex }
        ::= { onuIfTable 1 }

OnuIfEntry ::=
    SEQUENCE {
        onuIfStatisticsInOctets Counter64,
        onuIfStatisticsInUcastPkts Counter64,
        onuIfStatisticsInMulticastPkts Counter64,
        onuIfStatisticsInBroadcastPkts Counter64,
        onuIfStatisticsInDiscards Counter64,
        onuIfStatisticsInErrors Counter64,
        onuIfStatisticsInUnknownProtos Counter64,
        onuIfStatisticsOutOctets Counter64,
        onuIfStatisticsOutUcastPkts Counter64,
        onuIfStatisticsOutMulticastPkts Counter64,
        onuIfStatisticsOutBroadcastPkts Counter64,
        onuIfStatisticsOutDiscards Counter64,
        onuIfStatisticsOutErrors Counter64,
        onuIfStatisticsInBwUsage Counter64,
        onuIfStatisticsOutBwUsage Counter64,
        onuGemInOctets Counter64,
        onuGemInPackets Counter64,
        onuGemOutOctets Counter64,
        onuGemOutPackets Counter64,
        onuifIndex Integer32,
        onuifDescr String,
        onuifType INTEGER,
        onuifName String,
        onuifAdminStatus INTEGER,
        onuifOperStatus INTEGER,
        onuIfOnuPowerTx String,
        onuIfOnuPowerRx String,
        onuIfAlias String,
        onuSysUpTime TimeTicks
    }

-- tagpath /status/interface/ifTable/ifEntry/statistics/ifInOctets
onuIfStatisticsInOctets OBJECT-TYPE
    SYNTAX      Counter64
    MAX-ACCESS  read-only
    STATUS      current
    DESCRIPTION "Ethernet UNI input octets"
    ::= { onuIfEntry 8 }

-- tagpath /status/interface/ifTable/ifEntry/statistics/ifInUcastPkts
onuIfStatisticsInUcastPkts OBJECT-TYPE
    SYNTAX      Counter64
    MAX-ACCESS  read-only
    STATUS      current
    DESCRIPTION "Ethernet UNI input unicast packets"
    ::= { onuIfEntry 9 }

-- tagpath /status/interface/ifTable/ifEntry/statistics/ifInMulticastPkts
onuIfStatisticsInMulticastPkts OBJECT-TYPE
    SYNTAX      Counter64
    MAX-ACCESS  read-only
    STATUS      current
    DESCRIPTION "Ethernet UNI input multicast packets"
    ::= { onuIfEntry 10 }

-- tagpath /status/interface/ifTable/ifEntry/statistics/ifInBroadcastPkts
onuIfStatisticsInBroadcastPkts OBJECT-TYPE
    SYNTAX      Counter64
    MAX-ACCESS  read-only
    STATUS      current
    DESCRIPTION "Ethernet UNI input broadcast packets"
    ::= { onuIfEntry 11 }

-- tagpath /status/interface/ifTable/ifEntry/statistics/ifInDiscards
onuIfStatisticsInDiscards OBJECT-TYPE
    SYNTAX      Counter64
    MAX-ACCESS  read-only
    STATUS      current
    DESCRIPTION "Ethernet UNI input discarded packets"
    ::= { onuIfEntry 12 }

-- tagpath /status/interface/ifTable/ifEntry/statistics/ifInErrors
onuIfStatisticsInErrors OBJECT-TYPE
    SYNTAX      Counter64
    MAX-ACCESS  read-only
    STATUS      current
    DESCRIPTION "Ethernet UNI input packets with errors"
    ::= { onuIfEntry 13 }

-- tagpath /status/interface/ifTable/ifEntry/statistics/ifInUnknownProtos
onuIfStatisticsInUnknownProtos OBJECT-TYPE
    SYNTAX      Counter64
    MAX-ACCESS  read-only
    STATUS      current
    DESCRIPTION "Ethernet UNI input packets with unknown protocol"
    ::= { onuIfEntry 14 }

-- tagpath /status/interface/ifTable/ifEntry/statistics/ifOutOctets
onuIfStatisticsOutOctets OBJECT-TYPE
    SYNTAX      Counter64
    MAX-ACCESS  read-only
    STATUS      current
    DESCRIPTION "Ethernet UNI output octets"
    ::= { onuIfEntry 15 }

-- tagpath /status/interface/ifTable/ifEntry/statistics/ifOutUcastPkts
onuIfStatisticsOutUcastPkts OBJECT-TYPE
    SYNTAX      Counter64
    MAX-ACCESS  read-only
    STATUS      current
    DESCRIPTION "Ethernet UNI output unicast packets"
    ::= { onuIfEntry 16 }

-- tagpath /status/interface/ifTable/ifEntry/statistics/ifOutMulticastPkts
onuIfStatisticsOutMulticastPkts OBJECT-TYPE
    SYNTAX      Counter64
    MAX-ACCESS  read-only
    STATUS      current
    DESCRIPTION "Ethernet UNI output multicast packets"
    ::= { onuIfEntry 17 }

-- tagpath /status/interface/ifTable/ifEntry/statistics/ifOutBroadcastPkts
onuIfStatisticsOutBroadcastPkts OBJECT-TYPE
    SYNTAX      Counter64
    MAX-ACCESS  read-only
    STATUS      current
    DESCRIPTION "Ethernet UNI output broadcast packets"
    ::= { onuIfEntry 18 }

-- tagpath /status/interface/ifTable/ifEntry/statistics/ifOutDiscards
onuIfStatisticsOutDiscards OBJECT-TYPE
    SYNTAX      Counter64
    MAX-ACCESS  read-only
    STATUS      current
    DESCRIPTION "Ethernet UNI output discarded packets"
    ::= { onuIfEntry 19 }

-- tagpath /status/interface/ifTable/ifEntry/statistics/ifOutErrors
onuIfStatisticsOutErrors OBJECT-TYPE
    SYNTAX      Counter64
    MAX-ACCESS  read-only
    STATUS      current
    DESCRIPTION "Ethernet UNI output packets with errors"
    ::= { onuIfEntry 20 }

-- tagpath /status/interface/ifTable/ifEntry/statistics/ifInBwUsage
onuIfStatisticsInBwUsage OBJECT-TYPE
    SYNTAX      Counter64
    MAX-ACCESS  read-only
    STATUS      current
    DESCRIPTION "Ethernet UNI input bandwidth usage in bps"
    ::= { onuIfEntry 24 }

-- tagpath /status/interface/ifTable/ifEntry/statistics/ifOutBwUsage
onuIfStatisticsOutBwUsage OBJECT-TYPE
    SYNTAX      Counter64
    MAX-ACCESS  read-only
    STATUS      current
    DESCRIPTION "Ethernet UNI output bandwidth usage in bps"
    ::= { onuIfEntry 25 }

-- tagpath /status/interface/ifTable/ifEntry/statistics/gemInOctets
onuGemInOctets OBJECT-TYPE
    SYNTAX      Counter64
    MAX-ACCESS  read-only
    STATUS      current
    DESCRIPTION "GEM input octets"
    ::= { onuIfEntry 27 }

-- tagpath /status/interface/ifTable/ifEntry/statistics/gemInPkts
onuGemInPackets OBJECT-TYPE
    SYNTAX      Counter64
    MAX-ACCESS  read-only
    STATUS      current
    DESCRIPTION "GEM input packets"
    ::= { onuIfEntry 28 }

-- tagpath /status/interface/ifTable/ifEntry/statistics/gemOutOctets
onuGemOutOctets OBJECT-TYPE
    SYNTAX      Counter64
    MAX-ACCESS  read-only
    STATUS      current
    DESCRIPTION "GEM output octets"
    ::= { onuIfEntry 29 }

-- tagpath /status/interface/ifTable/ifEntry/statistics/gemOutPkts
onuGemOutPackets OBJECT-TYPE
    SYNTAX      Counter64
    MAX-ACCESS  read-only
    STATUS      current
    DESCRIPTION "GEM output packets"
    ::= { onuIfEntry 30 }

-- tagpath /status/interface/ifTable/ifEntry/ifIndex
onuifIndex OBJECT-TYPE
    SYNTAX      Integer32 (1 .. 2147483647)
    MAX-ACCESS  not-accessible
    STATUS      current
    DESCRIPTION "Table index"
    ::= { onuIfEntry 2 }

-- tagpath /status/interface/ifTable/ifEntry/ifDescr
onuifDescr OBJECT-TYPE
    SYNTAX      String (SIZE (0 .. 255))
    MAX-ACCESS  read-write
    STATUS      current
    DESCRIPTION "Interface description"
    ::= { onuIfEntry 3 }

-- tagpath /status/interface/ifTable/ifEntry/ifType
onuifType OBJECT-TYPE
    SYNTAX      INTEGER {other(1),regular1822(2),hdh1822(3),ddnX25(4),rfc877x25(5),ethernetCsmacd(6),iso88023Csmacd(7),iso88024TokenBus(8),iso88025TokenRing(9),iso88026Man(10),starLan(11),proteon10Mbit(12),proteon80Mbit(13),hyperchannel(14),fddi(15),lapb(16),sdlc(17),ds1(18),e1(19),basicISDN(20),primaryISDN(21),propPointToPointSerial(22),ppp(23),softwareLoopback(24),eon(25),ethernet3Mbit(26),nsip(27),slip(28),ultra(29),ds3(30),sip(31),frameRelay(32),rs232(33),para(34),arcnet(35),arcnetPlus(36),atm(37),miox25(38),sonet(39),x25ple(40),iso88022llc(41),localTalk(42),smdsDxi(43),frameRelayService(44),v35(45),hssi(46),hippi(47),modem(48),aal5(49),sonetPath(50),sonetVT(51),smdsIcip(52),propVirtual(53),propMultiplexor(54),ieee80212(55),fibreChannel(56),hippiInterface(57),frameRelayInterconnect(58),aflane8023(59),aflane8025(60),cctEmul(61),fastEther(62),isdn(63),v11(64),v36(65),g703at64k(66),g703at2mb(67),qllc(68),fastEtherFX(69),channel(70),ieee80211(71),ibm370parChan(72),escon(73),dlsw(74),isdns(75),isdnu(76),lapd(77),ipSwitch(78),rsrb(79),atmLogical(80),ds0(81),ds0Bundle(82),bsc(83),async(84),cnr(85),iso88025Dtr(86),eplrs(87),arap(88),propCnls(89),hostPad(90),termPad(91),frameRelayMPI(92),x213(93),adsl(94),radsl(95),sdsl(96),vdsl(97),iso88025CRFPInt(98),myrinet(99),voiceEM(100),voiceFXO(101),voiceFXS(102),voiceEncap(103),voiceOverIp(104),atmDxi(105),atmFuni(106),atmIma(107),pppMultilinkBundle(108),ipOverCdlc(109),ipOverClaw(110),stackToStack(111),virtualIpAddress(112),mpc(113),ipOverAtm(114),iso88025Fiber(115),tdlc(116),gigabitEthernet(117),hdlc(118),lapf(119),v37(120),x25mlp(121),x25huntGroup(122),transpHdlc(123),interleave(124),fast(125),ip(126),docsCableMaclayer(127),docsCableDownstream(128),docsCableUpstream(129),a12MppSwitch(130),tunnel(131),coffee(132),ces(133),atmSubInterface(134),l2vlan(135),l3ipvlan(136),l3ipxvlan(137),digitalPowerline(138),mediaMailOverIp(139),dtm(140),dcn(141),ipForward(142),msdsl(143),ieee1394(144),if-gsn(145),dvbRccMacLayer(146),dvbRccDownstream(147),dvbRccUpstream(148),atmVirtual(149),mplsTunnel(150),srp(151),voiceOverAtm(152),voiceOverFrameRelay(153),idsl(154),compositeLink(155),ss7SigLink(156),propWirelessP2P(157),frForward(158),rfc1483(159),usb(160),ieee8023adLag(161),bgppolicyaccounting(162),frf16MfrBundle(163),h323Gatekeeper(164),h323Proxy(165),mpls(166),mfSigLink(167),hdsl2(168),shdsl(169),ds1FDL(170),pos(171),dvbAsiIn(172),dvbAsiOut(173),plc(174),nfas(175),tr008(176),gr303RDT(177),gr303IDT(178),isup(179),propDocsWirelessMaclayer(180),propDocsWirelessDownstream(181),propDocsWirelessUpstream(182),hiperlan2(183),propBWAp2Mp(184),sonetOverheadChannel(185),digitalWrapperOverheadChannel(186),aal2(187),radioMAC(188),atmRadio(189),imt(190),mvl(191),reachDSL(192),frDlciEndPt(193),atmVciEndPt(194),opticalChannel(195),opticalTransport(196),propAtm(197),voiceOverCable(198),infiniband(199),teLink(200),q2931(201),virtualTg(202),sipTg(203),sipSig(204),docsCableUpstreamChannel(205),econet(206),pon155(207),pon622(208),bridge(209),linegroup(210),voiceEMFGD(211),voiceFGDEANA(212),voiceDID(213),mpegTransport(214),sixToFour(215),gtp(216),pdnEtherLoop1(217),pdnEtherLoop2(218),opticalChannelGroup(219),homepna(220),gfp(221),ciscoISLvlan(222),actelisMetaLOOP(223),fcipLink(224),rpr(225),qam(226),lmp(227),cblVectaStar(228),docsCableMCmtsDownstream(229),adsl2(230),macSecControlledIF(231),macSecUncontrolledIF(232),aviciOpticalEther(233),atmbond(234),voiceFGDOS(235),mocaVersion1(236),ieee80216WMAN(237),adsl2plus(238),dvbRcsMacLayer(239),dvbTdm(240),dvbRcsTdma(241),x86Laps(242),wwanPP(243),wwanPP2(244),voiceEBS(245),ifPwType(246),ilan(247),pip(248),aluELP(249),gpon(250),vdsl2(251),capwapDot11Profile(252),capwapDot11Bss(253),capwapWtpVirtualRadio(254),bits(255),docsCableUpstreamRfPort(256),cableDownstreamRfPort(257),vmwareVirtualNic(258),ieee802154(259),otnOdu(260),otnOtu(261),ifVfiType(262),g9981(263),g9982(264),g9983(265),aluEpon(266),aluEponOnu(267),aluEponPhysicalUni(268),aluEponLogicalLink(269),aluGponOnu(270),aluGponPhysicalUni(271),vmwareNicTeam(272),docsOfdmDownstream(277),docsOfdmaUpstream(278),gfast(279),sdci(280)}
    MAX-ACCESS  read-write
    STATUS      current
    DESCRIPTION "Global IANA interface type for this table entry"
    ::= { onuIfEntry 4 }

-- tagpath /status/interface/ifTable/ifEntry/ifName
onuifName OBJECT-TYPE
    SYNTAX      String (SIZE (0 .. 48))
    MAX-ACCESS  read-write
    STATUS      current
    DESCRIPTION "Interface name"
    ::= { onuIfEntry 5 }

-- tagpath /status/interface/ifTable/ifEntry/ifAdminStatus
onuifAdminStatus OBJECT-TYPE
    SYNTAX      INTEGER {up(1),down(2),testing(3)}
    MAX-ACCESS  read-write
    STATUS      current
    DESCRIPTION "Interface administrative state"
    ::= { onuIfEntry 6 }

-- tagpath /status/interface/ifTable/ifEntry/ifOperStatus
onuifOperStatus OBJECT-TYPE
    SYNTAX      INTEGER {up(1),down(2),testing(3),unknown(4),dormant(5),notPresent(6),lowerLayerDown(7)}
    MAX-ACCESS  read-write
    STATUS      current
    DESCRIPTION "Interface operational state"
    ::= { onuIfEntry 7 }

-- tagpath /status/interface/ifTable/ifEntry/if-power-tx
onuIfOnuPowerTx OBJECT-TYPE
    SYNTAX      String
    MAX-ACCESS  read-write
    STATUS      current
    DESCRIPTION "ONU Tx optical power"
    ::= { onuIfEntry 21 }

-- tagpath /status/interface/ifTable/ifEntry/if-power-rx
onuIfOnuPowerRx OBJECT-TYPE
    SYNTAX      String
    MAX-ACCESS  read-write
    STATUS      current
    DESCRIPTION "ONU Rx optical power"
    ::= { onuIfEntry 22 }

-- tagpath /status/interface/ifTable/ifEntry/ifAlias
onuIfAlias OBJECT-TYPE
    SYNTAX      String (SIZE (0 .. 64))
    MAX-ACCESS  read-only
    STATUS      current
    DESCRIPTION "Interface textual description"
    ::= { onuIfEntry 23 }

-- tagpath /status/interface/ifTable/ifEntry/sys-uptime
onuSysUpTime OBJECT-TYPE
 SYNTAX TimeTicks
    MAX-ACCESS  read-only
    STATUS      current
    DESCRIPTION "ONU system uptime"
    ::= { onuIfEntry 26 }

END
