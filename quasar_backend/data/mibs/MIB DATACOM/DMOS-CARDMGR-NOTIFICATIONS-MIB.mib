DMOS-CARDMGR-NOTIFICATIONS-MIB DEFINITIONS ::= BEGIN

IMPORTS
    MODULE-IDENTITY,
    OBJECT-TYPE,
    NOTIFICATION-TYPE,
    Integer32
        FROM SNMPv2-SMI
    OBJECT-GROUP,
    NOTIFICATION-GROUP
        FROM SNMPv2-CONF
    dmosNotifications,
    notificationTime,
    notificationName,
    notificationSourceType,
    notificationSourceValue,
    notificationSeverity,
    notificationInfo,
    notificationAlarmState
        FROM DMOS-NOTIFICATIONS-MIB;

dmosCardmgrNotificationsMIB MODULE-IDENTITY
    LAST-UPDATED "201711270000Z"
    ORGANIZATION    "DATACOM"
    CONTACT-INFO
                "DATACOM

                 Postal: DATACOM
                     Rua America, 1000
                     Eldorado do Sul, RS
                     CEP 92990-000
                             BRAZIL

                 Tel:+55(51)3933 3000
                 Fax:+55(51)3933 3003

                 E-mail: datacom@datacom.ind.br "
    DESCRIPTION
        "DmOS notifications related to card manager events."
    REVISION "201711270000Z"
    DESCRIPTION
        " First release "
    ::= { dmosNotifications 3 }

dmosCardmgrNotificationGroups OBJECT IDENTIFIER ::= { dmosCardmgrNotificationsMIB 1 }

dmosCardmgrAlarmTrapsGroup NOTIFICATION-GROUP
    NOTIFICATIONS { cardNotProvisionedAlarmTrap,
                    cardNotPresentAlarmTrap,
                    cardRemovedAlarmTrap,
                    cardMismatchAlarmTrap,
                    fanModuleNotPresentAlarmTrap }

    STATUS      current
    DESCRIPTION "Traps generated by card manager alarms."
    ::= { dmosCardmgrNotificationGroups 1 }

cardNotProvisionedAlarmTrap    NOTIFICATION-TYPE
    OBJECTS {
        notificationTime,
        notificationName,
        notificationSourceType,
        notificationSourceValue,
        notificationSeverity,
        notificationInfo,
        notificationAlarmState }

    STATUS        current
    DESCRIPTION   "Card not provisioned alarm trap."
    ::=  {  dmosCardmgrNotificationsMIB 2 }

cardNotPresentAlarmTrap    NOTIFICATION-TYPE
    OBJECTS {
        notificationTime,
        notificationName,
        notificationSourceType,
        notificationSourceValue,
        notificationSeverity,
        notificationInfo,
        notificationAlarmState }

    STATUS        current
    DESCRIPTION   "Card not present alarm trap."
    ::=  {  dmosCardmgrNotificationsMIB 3 }

cardRemovedAlarmTrap    NOTIFICATION-TYPE
    OBJECTS {
        notificationTime,
        notificationName,
        notificationSourceType,
        notificationSourceValue,
        notificationSeverity,
        notificationInfo,
        notificationAlarmState }

    STATUS        current
    DESCRIPTION   "Card removed alarm trap."
    ::=  {  dmosCardmgrNotificationsMIB 4 }

cardMismatchAlarmTrap    NOTIFICATION-TYPE
    OBJECTS {
        notificationTime,
        notificationName,
        notificationSourceType,
        notificationSourceValue,
        notificationSeverity,
        notificationInfo,
        notificationAlarmState }

    STATUS        current
    DESCRIPTION   "Card mismatch alarm trap."
    ::=  {  dmosCardmgrNotificationsMIB 5 }

cardInsertedTrap    NOTIFICATION-TYPE
    OBJECTS {
        notificationTime,
        notificationName,
        notificationSourceType,
        notificationSourceValue,
        notificationInfo }

    STATUS        current
    DESCRIPTION   "Card inserted trap."
    ::=  {  dmosCardmgrNotificationsMIB 6 }

cardRemovedTrap    NOTIFICATION-TYPE
    OBJECTS {
        notificationTime,
        notificationName,
        notificationSourceType,
        notificationSourceValue,
        notificationInfo }

    STATUS        current
    DESCRIPTION   "Card removed trap."
    ::=  {  dmosCardmgrNotificationsMIB 7 }

fanModuleNotPresentAlarmTrap    NOTIFICATION-TYPE
    OBJECTS {
        notificationTime,
        notificationName,
        notificationSourceType,
        notificationSourceValue,
        notificationSeverity,
        notificationInfo,
        notificationAlarmState }

    STATUS        current
    DESCRIPTION   "Fan module not present alarm trap."
    ::=  { dmosCardmgrNotificationsMIB 8 }

cardUpdatedTrap    NOTIFICATION-TYPE
    OBJECTS {
        notificationTime,
        notificationName,
        notificationSourceType,
        notificationSourceValue,
        notificationInfo }

    STATUS        current
    DESCRIPTION   "Card updated trap."
    ::=  {  dmosCardmgrNotificationsMIB 9 }

psuUnsupportedAlarmTrap    NOTIFICATION-TYPE
    OBJECTS {
        notificationTime,
        notificationName,
        notificationSourceType,
        notificationSourceValue,
        notificationSeverity,
        notificationInfo,
        notificationAlarmState }

    STATUS        current
    DESCRIPTION   "PSU not supported in this product."
    ::=  { dmosCardmgrNotificationsMIB 10 }

cardUninitializedAlarmTrap    NOTIFICATION-TYPE
    OBJECTS {
        notificationTime,
        notificationName,
        notificationSourceType,
        notificationSourceValue,
        notificationSeverity,
        notificationInfo,
        notificationAlarmState }

    STATUS        current
    DESCRIPTION   "Card could not be correctly initialized."
    ::=  {  dmosCardmgrNotificationsMIB 11 }

END
